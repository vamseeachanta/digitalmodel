(defun c:1(/ a)
  (setq a 0)
  (while (setq ob (entsel))
    (command "area" "ob" ob)
    (setq a (+ a (getvar "area")))
    )
  (TypeArea a)
    )
(defun TypeArea(a / pp)
  (setq pp (getpoint "Pick point to write to:")
	ht (getreal "Text Hight:")
	a (rtos a 2 3))
  (command "Text" pp ht 0 a)
  )
