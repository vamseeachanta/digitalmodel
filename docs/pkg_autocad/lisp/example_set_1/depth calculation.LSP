(defun c:x1 (/ txt1 txt2 txpn txv1 txv2 v1 v2 v0 txt y0 txtpnt)
  (while (setq tx1 (entget (car (entsel "\nselect text1:"))))
    (progn
      (setq tx2 (entget (car (entsel "\nselect text2:"))))
      (setq txv1 (cdr (assoc '1 tx1)))
      (setq txpn (cdr (assoc '10 tx2)))
      (setq txv2 (cdr (assoc '1 tx2)))
      (setq v1 (atof txv1)
	    v2 (atof txv2)
      ) ;_ end of setq
      (setq v0 (- v2 v1))
      (setq txt (rtos v0 2 3))
      (setq y0 (car txpn)
	    y1 (cadr txpn)
	    y2 (- y1 62.25)
      )
      (setq txtpnt (list y0 y2))
      (command "osnap" "none")
      (if (<= v0 0.00)
	(command "layer" "set" "defc" "")
	(command "layer" "set" "deff" "")
      )
      (COMMAND "TEXT" "S" "" txtpnt "90" txt)
    ) ;_ end of progn
  ) ;_ end of while
)
(defun C:d (/ pt1 pt2 datum PT1Y PT2Y PT2L PT2X)
  (COMMAND "-OSNAP" "ENDPOINT")
  (setq pt1 (getpoint "insrtfirestpoint"))
 (setq datum (GETREAL "insetr datum"))
  ;(setq datum 375.00)
  (COMMAND "-OSNAP" "INTersection")
  (WHILE (setq pt2 (getpoint "insrtsecondpoint"))
    (setq pt1y (cadr pt1))
    (setq pt2y (cadr pt2))
    (setq pt2x (+ (car pt2) 0))
    (SETQ PT2L (RTOS (+ (/ (- PT2Y PT1Y) 10) DATUM) 2 3))
    (SETQ TX1PT (LIST (+ PT2X 4) (- PT1Y 103.51)))
    (COMMAND "LAYER" "SET" "DRLEVEL" "")
    (command "OSNAP" "NONE")
    (COMMAND "TEXT" "S" "PRO1 " TX1PT "90" PT2L)
    (COMMAND "-OSNAP" "INTersection")
  )
)
