(defun C:REG()
	(setq name (getvar "dwgname"))
        (setq sname (substr name 1 8))
        (setq pat "c:\\work\\")         
	(setq regfil (strcat pat sname ".reg"))
	(initget "Screen File")
	(setq ans (getkword"\n>>PARCEL'S AREA FORM SCREEN OR FILE?(S/F):"))
(setq opti
	(cond
        ((eq ans "Screen")      1)
        ((eq ans "File")      2)))
	(initget 1)
(if (= opti 1)
	(progn
	(setq reg (open regfil "w"))
	(setq ct 1.0)
	(setq num (getint"\nENTER NUMBER OF PARCLES:"))
	(setq num1 (1+ num))
	(while (< ct num1)
	      (progn
	      (setq sct (rtos ct 2 0))
	      (SETQ AREA (getSTRING (strcat "\nENTER AREA OF PAR #" SCT ":")))
	      (setq za (atoi sct))			
	      (princ "(" reg)
	      (princ za reg)
	      (princ " " reg)
	      (princ area reg)
	      (princ ")" reg)
	      (princ "\n" reg)
	      (setq ct (1+ ct))
	      )	
	)
(close reg)
		)
)
(princ)
(if (= opti 2)
	(progn
	(setq regfil (getfiled "SELECT AREA'S FILE" "C:/acadwin/work/" "REG" 8))
	)
)
		(setq arefil (strcat pat sname ".are"))
	(setq rare (getreal"\nENTER REAL AREA:"))
	(SETQ VAL (GETREAL "\nENTER REGESTRATION VALUE:"))
	(SETQ TOT 0)
(princ "                              Working ... Please Wait")
		(setq reg (open regfil "r"))
		(setq are (open arefil "w"))
		(princ "\n  POINT N#       A R E A      REG.VALUE" are)
		(PRINc "\n  ========       =======      =========" are)
(if reg
	(progn
		(while (setq pnt (read-line reg))
			(setq LPNT (READ PNT))
			(SETQ REC (car lpnt))
			(setq area (cadr lpnt))
			(setq tot (+ tot area))
		)
	)
)
(close reg)
		(SETQ STR (- rare TOT))
		(SETQ CALV (/ VAL TOT))
		(setq reg (open regfil "r"))
(if reg
	(progn
		(while (setq pnt (read-line reg))
			(setq LPNT (READ PNT))
			(SETQ REC (car lpnt))
			(setq area (cadr lpnt))
			(SETQ REGVAL (* AREA CALV))
			(princ "\n" are)
			(princ "     " are)	
			(princ  REC are)
			(princ "             " are)
			(SETQ AREA (RTOS AREA 2 2))
			(SETQ REGVAL (RTOS REGVAL 2 3))
			(princ AREA are)
			(princ "        " are)
			(princ regval are)
		)
	)
)
(princ "\n" are)
(PRINC "  " are)
(princ "STREET" are)
(PRINC "           " are)
(SETQ STR (RTOS STR 2 2))
(PRINC STR are)
(PRINC "        " are)
(PRINC "0.000" are)
(PRINc "\n  ========       =======      =========" are)
(princ "\n" are)
(PRINC "  " are)
(princ " TOTAL" are)
(PRINC "           " are)
(PRINC RARE are)
(PRINC "        " are)
(PRINC VAL are)
(CLOSE reg)
(close are)
(initget "Yes NO")
(setq ans (getkword"\n>>DO YOU WISH TO SEE RESULTS ON SCREEN(Y/N):"))
(setq opt
	(cond
        ((eq ans "Yes")      1)
        ((eq ANS "No")      2)))
	(initget 1)
(if (= opt 1)
	(progn
	(command "show" arefil)
	)
)
(princ)
)
