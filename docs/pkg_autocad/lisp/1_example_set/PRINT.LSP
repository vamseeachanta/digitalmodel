(defun c:cor()
(command "osnap" "node")
(setq i (open "c:\\WELL\\gcor.XYZ" "w"))
(setq cnt 1)
(while (setq pn (getpoint "\nplease select your point:"))
(setq x (car pn))
(setq y (cadr pn))
(setq z (caddr pn))
(setq x (rtos x 2 3))
(setq y (rtos y 2 3))
(setq z (rtos z 2 3))
(princ cnt i)
(princ "  " i)
(princ x i)
(princ "  " i)
(princ y i)
(princ "   " i)
(princ z i)
(setq cnts (rtos cnt 2 0))
(setq hi (getvar "pdsize"))
(setq npn (polar pn (* hi 2) 0.77))
(command "text" npn 2 0 cnts)
(setq cnt (1+ cnt))
(princ "\n" i)
)
(close i)
)
