(defun c:gg (/ p1 p2 p3 p4 p01 p11 p21 p31 p41 pn px py pz ip in p02 p0n p12 p0x
	       p22 p0y p32 p0z p42) 
  (setq	p0  (getpoint "\n enter uper left of schedule")
        p1  (list (+ (car p0) 5) (cadr p0))
	p2  (list (+ (car p0) 12) (cadr p0))
	p3  (list (+ (car p0) 19) (cadr p0))
	p4  (list (+ (car p0) 26) (cadr p0))
	p01 (list (car p0) (- (cadr p0) 2))
	p11 (list (car p1) (- (cadr p1) 2))
	p21 (list (car p2) (- (cadr p2) 2))
	p31 (list (car p3) (- (cadr p3) 2))
	p41 (list (car p4) (- (cadr p4) 2))
	pn  (list (+ (car p0) 1.5) (- (cadr p0) 1.2))
	px  (list (+ (car p1) 2.5) (- (cadr p1) 1.2))
	py  (list (+ (car p2) 2.5) (- (cadr p2) 1.2))
	pz  (list (+ (car p3) 2.5) (- (cadr p3) 1.2))
  )
  (setvar "osmode" 0)		 
  (setvar "angdir" 1)			
  (setvar "angbase" 1.5708)		
  (setvar "aunits" 2)			
  (command "rectang" p0 p11)		
  (command "rectang" p1 p21)
  (command "rectang" p2 p31)
  (command "rectang" p3 p41)
  (command "text" pn "0.7" 100 "point")
  (COMMAND "text" px "1" 100 "E")
  (COMMAND "text" py "1" 100 "N")
  (command "text" pz "1" 100 "Z")	   
  (setvar "osmode" 553)
  (setq num (getint "\n FIRST POINT NUMBER:"))
  (setq ctr (- num 1))
  (while (setq ip  (getpoint "\n enter a point to write its coordinate")
	       ctr (+ ctr 1)
	       xtx (+ 0.1 (car ip))
	       ytx (+ 0.1 (cadr ip ))
	       tx  (list xtx ytx )
	       p02 (list (car p01) (- (cadr p01) 2))
	       p0n (list (+ (car p02) 0.3) (+ (cadr p02) 0.3))
	       p12 (list (+ (car p01) 5) (- (cadr p01) 2))
	       p0x (list (+ (car p12) 0.5) (+ (cadr p12) 0.3))
	       p22 (list (+ (car p01) 12) (- (cadr p01) 2))
	       p0y (list (+ (car p22) 0.5) (+ (cadr p22) 0.3))
	       p32 (list (+ (car p01) 19) (- (cadr p01) 2))
	       p0z (list (+ (car p32) 0.5) (+ (cadr p32) 0.3))
	       p42 (list (+ (car p01) 26 ) (- (cadr p01) 2))
	 )
    (setvar "osmode" 0)
    (command "color" 1)
    (command "rectang" p01 p12)
    (command "rectang" p11 p22)
    (command "rectang" p21 p32)
    (command "rectang" p31 p42)
    (command "color" 3)
    (command "text" p0n "1" 100 ctr)
    (command "text" tx "1" 100 ctr)
    (command "point" ip)
    (command "color" 5)
    (command "text" p0x "0.6" 100 (rtos (car ip) 2 3))
    (command "text" p0y "0.6" 100 (rtos (cadr ip) 2 3))
    (command "text" p0z "0.6" 100 (rtos (caddr ip) 2 3))
    (setvar "osmode" 553)
    (setq p01 p02
    )
  )
)
	   (princ)
