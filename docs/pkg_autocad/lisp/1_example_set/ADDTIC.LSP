(defun C:ATIC ()
(defun *error* (msg)
	(princ "error: ")
	(princ msg)
	(terpri)
)
	(setvar "cmdecho" 0)
	(graphscr)
	(command "tablet" "on")
	(setq fnam (getvar "dwgname")
		fxt ".mtc"
		rfxt ".rtc"
		fname (strcat fnam fxt)
		rfnam (strcat fnam rfxt)
		f (open fname "a")
		S (open rfnam "a")
		num (getint "\nNUMBER OF USED REFERENCE POINTS:")
		test 1
		num1 (+ 1 num)
	)
	(while (< test num1)
		(progn
			(setq stest (rtos test 2 0))
			(setq al (getpoint (STRCAT "\nCHOOSE POINT #" stest " FROM TABLET:")))
			(command "point" al)
			(setq xr (getreal "\nENTER X - COORDINATE: ")
				yr (getreal "\nENTER Y - COORDINATE: ")
				xm (car al)
				ym (cadr al)
				xm (rtos xm 2 4)
				ym (rtos ym 2 4)
			)
			(princ "(" f)
			(princ xm f)
			(princ " " f)
			(princ ym f)
			(princ ")" f)
			(princ "\n" f)
			(setq xr (rtos xr 2 4)
				yr (rtos yr 2 4)
			)
			(princ "(" s)
			(princ xr s)
			(princ " " s)
			(princ yr s)
			(princ ")" s)
			(princ "\n" s)
			(setq test (1+ test))
		)
	)
(close f)
(close S)
	(command "tablet" "off")
)
