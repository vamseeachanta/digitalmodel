(setq fn (strcat ipec#elsppath "screen.msg"))
(setq filnm (open fn "r"))
(setq txt (read-line filnm))
(setq cnt (atoi (read-line filnm)))
(close filnm)
(if (> cnt 0)
  (progn
    (setq filnm (open fn "w"))
    (write-line txt filnm)
    (setq cnt (1- cnt))
    (setq num (itoa cnt))
    (write-line num filnm)
    (close filnm)
    (setq tx (strcat "\n" txt " (will display " num " more times)."))
    (princ tx)(princ)
  )
)
