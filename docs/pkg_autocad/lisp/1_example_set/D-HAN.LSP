; Duong han
(defun C:DH ( / p1 p2 p3 p4 a b l n deltaX deltaY i x1 y1 x2 y2 )
       (setq p1 (getpoint "Start point : ") )
       (setq p2 (getpoint p1 "End point   : ") )
;       (setq a  (getdist  "Distance    : ") )
;       (setq b  (getdist  "Lenght      : ") )
       (setq a 1.0)
       (setq b 1.0 )	
       (setq l  (distance p1 p2) )
       (setq n  (fix ( / l a ) ) )
       (setq deltaX ( - (car p2) (car p1) ) )
       (setq deltaY ( - (cadr p2) (cadr p1) ) )
       (setq i 0)
       (setvar "OSMODE" 0)
       (command "_UNDO" "_GROUP")
       (while (<= i n)
        (setq x1 ( + (car p1) (* i (* (/ a l) deltaX )  
                              )
                 ) 
        )
        (setq y1 ( + (cadr p1) (* i (* ( / a l ) deltaY ) 
                               )
                 ) 
        )
        (setq p3 (list x1 y1) )
        (setq x2 ( + x1 (* -1 (* b (/ deltaY l) )
                        ) 
                 ) 
        ) 
        (setq y2 ( + y1 (* b (/ deltaX l) 
                        )
                 )
        ) 
        (setq p4 (list x2 y2) )
        (command "LINE" p3 p4 "")
        (setq i (+ i 1) )
       )
       (command "_UNDO" "_END")
       (setvar "OSMODE" 177)
       (princ)
)
