(defun C:PLJOIN (/ echo ss fuzz)
  (setq echo (getvar "CMDECHO"))
  (setvar "CMDECHO" 0)
  (setq ss (ssget)
        fuzz (getdist "Fuzz distance: ") )
  (command "_pedit" "_M" ss "" "_Y" "_J" fuzz "")
  (setvar "CMDECHO" echo)
  (princ)
)
