(DEFUN C:LBL()
(defun *error* (msg)
	(princ "error: ")
	(princ msg)
	(terpri)
)
	(command "LAYER" "THAW" "LABEL" "")
	(COMMAND "COLOR" "bylayer")
	(command "LAYER" "SET" "LABEL" "c" 6 "" "")
	(SETQ pt (GETPOINT"\nWHERE TO PLACE LABLE ?"))
		(command "text" "m" pt 2 0)
)
