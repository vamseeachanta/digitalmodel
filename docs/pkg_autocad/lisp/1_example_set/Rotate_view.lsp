(defun c:rv ()
    (setvar "cmdecho" 0)
    (command "tilemode" 0)
    (command "mspace")
    (setq p1 (getpoint "\nPick First Insertion Point...."))
    (setq p2 (getpoint p1 "\nPick Second Insertion point...."))
    (setq d1 (distance p1 p2))
    (setq d (/ d1 2.00))
    (setq a1 (angle p1 p2))
    (setq a1 (* a1 57.29578))
    (command "_.DVIEW" "" "_TW" (- a1) "")
    (setvar "cmdecho" 1)
    (princ)
  )
