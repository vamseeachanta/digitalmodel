(defun c:NMBR()
  (setq sset (ssget))
     (setq count 0)
      (setq slen (sslength sset))
      (setq value (getreal "\nEnter Starting Number: "))
      (while ( < count slen)
           (setq sget (entget (ssname sset count)))
	   (setq asget (assoc 1 sget))
	   (setq nstr (rtos value 2 0))
	   (setq sget (subst (cons 1 nstr) asget sget))
	   (entmod sget)
	(setq value (+ value 1))
		   (setq count (1+ count))
      )
    (princ)
)
