(defun c:fileread ()

 (setq pp1(getfiled "Select a data file" "" "CSV" 0))

  (setq textht (getreal "\nEnter a Text Height <1>:"))
  (if (= textht nil)
    (setq textht 1)
  )
  (setq pointsz (getreal "\nEnter a Point size <.3> :"))
  (if (= pointsz nil)
    (setq pointsz 0.3)
  )
  (setvar "cmdecho" 0)
  (setq ff (open pp1 "r"))
  (command "-style" "rs" "Romans" textht ".8" "0" "" "" "")
  (setvar "osmode" 0)
  (setvar "luprec" 3)
  (command "-layer" "n" "SPNT" "c" "red" "SPNT" "")
  (command "-layer" "n" "PTCO" "c" "yellow" "PTCO" "")
  (command "-layer" "n" "LEV" "c" "magenta" "LEV" "")
  (command "-layer" "n" "PTXT" "c" "green" "PTXT" "")
  (while
    (setq f (read-line ff))
     (setq l1 (strlen f))
     (setq l2 (vl-string-search "," f))
     (setq f2 (substr f 1 l2))
     (setq east f2)
     (setq ff1 (substr f (+ l2 2) (- l1 (+ l2 1))))
     (setq l3 (vl-string-search "," ff1))
     (setq f2 (substr ff1 1 l3))
     (setq north f2)
     (setq l1 (strlen ff1))
     (setq ff2 (substr ff1 (+ l3 2) (- l1 (+ l3 1))))
     (setq l4 (vl-string-search "," ff2))
     (setq f2 (substr ff2 1 l4))
     (setq ele f2)
     (setq l1 (strlen ff2))
     (setq ff3 (substr ff2 (+ l4 2) (- l1 l4)))
     (setq pid ff3)
     (setq east1 (atof east))
     (setq north1 (atof north))
     (setq ele1 (atof ele))
     (setq co1 (list east1 north1 ele1))
     (command "point" co1)
     (command "chprop" (entlast) "" "la" "spnt" "")
    (command "insert" "d:/implisp/sree.dwg" co1 "" "" "" pid ele east north )
    )
  (close ff)
  (setvar "pdmode" 3)
  (command "pdsize" pointsz)
  (command "layer" "f" "lev" "f" "ptco" "")
  (command "zoom" "e")
)
(princ "\nType fileread at Command Prompt:")
(princ)

					;Command: (substr "abcde" 3 2) 
					;"cd"
