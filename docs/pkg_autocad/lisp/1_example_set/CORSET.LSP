(defun C:SET()
(defun *ERROR* (MSG)
	(princ "error: ")
	(princ msg)
	(terpri)
)
	(command "LAYER" "THAW" "0" "")
	(command "LAYER" "SET" "0" "")
	(setvar "cmdecho" 0)
	(setq fnam (getSTRING"\nENTER FILE NAME:"))
	(setq rext ".RCR")
	(setq rcfnam (strcat fnam rext))
	(graphscr)
(princ "                              Working ... Please Wait!")
		(setvar "pdmode" 32)
		(setvar "pdsize" 5)
		(command "color" 4)
		(command "ucsicon" "off")
		(setq i (open rcfnam "r"))
(if i
	(progn
		(while (setq pnt (read-line i))
			(setq pnt (read pnt))
			(command "point" pnt "")
			(setq pntp pnt)
		)
	)
)
(close i)
(command "zoom" "a")
)
