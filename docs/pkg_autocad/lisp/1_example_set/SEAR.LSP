(DEFUN C:sea()
(command "osnap" "none")
(setq txt (getstring"\nWHICH POINT NUMBER:"))
(setq ds (getreal"\nDistance Range:"))
(setq ent1 (ssget "X" '((0 . "text"))))
(setq num (sslength ent1))
(setq cnt 0)
(repeat num
(setq s1 (ssname ent1 cnt))
(setq s2 (entget s1))
(setq stxt (cdr (assoc 1 s2)))
(if (= txt stxt)
	(progn
	(setq pnt (cdr (assoc 10 s2)))
	(setq p1 (polar pnt 3.9 ds))
	(setq p2 (polar pnt 0.8 ds))
	(prompt "\n                    I Found it....")
	(command "zoom" "w" p1 p2)
	(setq cnt (- NUM 1))
	)
)
(setq cnt (1+ cnt))
)
(prompt "\n                    SEARCHING IS DONE")
)
