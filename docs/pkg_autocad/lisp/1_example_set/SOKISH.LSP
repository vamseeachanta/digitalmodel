;************** CONVERSION OF TC1700 FILE TO DWG FILE TXT FILE ***********
(defun C:SOK()
(defun *ERROR* (MSG)
	(princ "error: ")
	(princ msg)
	(terpri)
)
;(setq pass (findfile "c:/win95/clock.hlp"))
;(if pas7
;(progn
(command "filedia" "0")
;#####################################################
	(setq po 1)
	(setq posi 1)
	(command "LAYER" "new" "disc" "")
	(command "LAYER" "new" "PTLBL" "")
	(command "LAYER" "THAW" "0" "")
	(command "LAYER" "SET" "0" "")
	(command "osnap" "non")
	(setvar "cmdecho" 0)
	(setq fnam (getSTRING"\nENTER FILE NAME:"))
	(setq rext ".sdr")
	(setq cext ".con")
	(setq rcfnam (strcat fnam rext))
	(setq ccfnam (strcat fnam cext))
	(graphscr)
(princ "                              Working ... Please Wait!")
		(setvar "pdmode" 32)
                (setvar "pdsize" 0.5)
	;	(command "color" 4)
		(command "ucsicon" "off")
		(setq i (open rcfnam "r"))
		(setq j (open ccfnam "w"))
(if i
	(progn
		(while (setq pnt (read-line i))
                        (if (= (substr pnt 1 4) "08TP")
				(progn
			(setq ptn (substr pnt 13 8))
				(repeat 7
					(setq flp (substr ptn 1 1))
                                        (if (= flp "0")
						(progn
							(setq ptn (substr ptn 2 (- 8 posi)))
						)
					)
				(setq posi (+ posi 1))
				)
				(setq posi 1)
						(setq xa (substr pnt 21 9))
						(setq x (atof xa))
						(setq ya (substr pnt 37 9))
						(setq y (atof ya))
						(setq za (substr pnt 51 9))
						(setq z (atof za))
						(setq pdis (substr pnt 69 8))
                                                (setq pdis1 (substr pnt 69 1))
        (command "layer" "m" pdis1 "C" (ASCII PDIS1) "" "")           
			(setq poit (list x y z))
			(command "point" poit)
			(setq poil (list x y))
	(command "LAYER" "s" "PTLBL" "")
			(command "text" poil "" "" ptn)
	(command "LAYER" "s" "disc" "")
			(command "text" "" pdis)
	(command "LAYER" "s" "0" "")
			(setq ptnl (strlen ptn))
			(if (= ptnl 3)
				(princ " " j))
			(if (= ptnl 2)
				(princ "  " j))
			(if (= ptnl 1)
				(princ "   " j))
			(PRINC Ptn)
			(PRINC Ptn j)
			(princ "   " j)
			(princ x j)
			(princ "   " j)
			(princ y j)
			(princ "   " j)
			(princ z j)
			(princ "\n")
			(princ "\n" j)
			)
			)
;********************************************************
			(if (= (substr pnt 1 4) "02IC")
				(progn
			(setq ptn (substr pnt 13 8))
				(repeat 7
					(setq flp (substr ptn 1 1))
					(if (= flp " ")
						(progn
							(setq ptn (substr ptn 2 (- 8 posi)))
						)
					)
				(setq posi (+ posi 1))
				)
				(setq posi 1)
						(setq xa (substr pnt 37 9))
						(setq x (atof xa))
						(setq ya (substr pnt 21 9))
						(setq y (atof ya))
						(setq za (substr pnt 51 9))
						(setq z (atof za))
			(setq poit (list x y z))
			(command "point" poit)
			(setq poil (list x y))
	(command "LAYER" "s" "PTLBL" "")
			(command "text" "" "" poil "" ptn)
	(command "LAYER" "s" "disc" "")
			(command "text" "" "" poil "" "CONTROL-P")
	(command "LAYER" "s" "0" "")
			(setq ptnl (strlen ptn))
			(if (= ptnl 3)
				(princ " " j))
			(if (= ptnl 2)
				(princ "  " j))
			(if (= ptnl 1)
				(princ "   " j))
			(PRINC Ptn)
			(PRINC Ptn j)
			(princ "   " j)
			(princ x j)
			(princ "   " j)
			(princ y j)
			(princ "   " j)
			(princ z j)
			(princ "\n")
			(princ "\n" j)
			)
			)
;********************************************************
;		)
;	)
)
(close i)
(close j)
(command "zoom" "e")
(command "filedia" "1")
;#####################################################
)
)
;(if (= pass nil) (alert "  TO RUN THIS PROGRAM CORRECTLY \n    PLEASE CONTACT TEL  615300 \n         G E O G R A P H"))
(princ)
)
