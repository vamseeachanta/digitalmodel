(pt2block "well" 100)

(defun pt2block (bname scale / ss i ent elist)
(if (and (tblobjname "BLOCK" bname)
(setq ss (ssget '((0 . "POINT"))))
)
(progn
(setq i -1)
(while (setq ent (ssname ss (setq i (1+ i))))
(setq elist (entget ent))
(entmake (list (cons 0 "INSERT")
(cons 2 bname)
(assoc 10 elist)
(assoc 8 elist)
(cons 41 scale)
(cons 42 scale)
(cons 43 scale)
(cons 50 0)
)
)
(entdel ent)
)
)
)
)

CADMiester
