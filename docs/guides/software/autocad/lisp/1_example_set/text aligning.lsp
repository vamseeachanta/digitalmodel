;*********************************************************************
;THIS PROGRAMME ALLIGNS THE TEXTS WITH REFERENCE TO THE PICKING POINTS
;*********************************************************************
(defun dtr (a)
 (* pi (/ a 180.0))
)

(defun c:EDT()
   (setq olunt (getvar "lunits"))
;   (command "units" "2" "4" "2" "4" "" "n")
   (setvar "cmdecho" 0)(setvar "blipmode" 0)(setvar "highlight" 1)
   (setvar "orthomode" 0)
   (SETQ s1 1 tang 0)
   (graphscr)
   (Prompt "\nChange rotation angle appropriately: ")    
     (setq s (ssget)
           c 0
          s1 (sslength s))
	  (SETVAR "OSMODE" 512)
	  (setq rot1pt (getpoint "\nFIRST Point for ROT. angle :"))
	  (setq rot2pt (getpoint rot1pt "\nSECOND Point. :"))
	  (setq tang (angtos (angle rot1pt rot2pt) 0 2))
	  (SETVAR "OSMODE" 0) 
  (while (> s1 0)
     (setq ent (entget (ssname s c))
           lot_no (cdr (assoc 1 ent))
           tin1pt (cdr (assoc 10 ent))
     )
     (setq tang1 (dtr (atof tang)))
     (setq set1 (subst (cons 1 lot_no) (assoc 1 ent) ent)
          set2 (subst (cons 50 tang1) (assoc 50 ent) ent))
     (setq c (1+ c))
     (if (> s1 0)
      (progn
       (entmod set1)
       (entmod set2)
      )
     )
     (setq s1 (1- s1))
    )
    (setvar "lunits" olunt)
)
