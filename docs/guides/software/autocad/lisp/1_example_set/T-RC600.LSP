(defun c:to-tc()
(defun *error* (msg)
       (princ "error: ")
       (princ msg)
       (terpri)
)
===========================
(setq ha (getvar "pdsize"))
(setq pds (* ha 2.0))
(setq pass (getvar "maxsort"))
(if (= pass 1001)
(progn
(setq i (open "c:/tc600/tc.xyz" "w"))
(prompt "...        Select Your Point Please      ...")
(princ "                              Working ... Please Wait!")
(setq ent1 (ssget '((0 . "point"))))
(setq num (sslength ent1))
(setq cnt 0)
(repeat num
(setq s1 (ssname ent1 cnt))
(setq s2 (entget s1))
(setq pnt (cdr (assoc 10 s2)))
(setq x (car pnt))
(setq y (cadr pnt))
(setq inx (fix x))
(setq iny (fix y))
(setq x (rtos x 2 3))
(setq y (rtos y 2 3))
(setq sinx (rtos inx 2 0))
(setq siny (rtos iny 2 0))
(setq lsx (strlen sinx))
(setq lsy (strlen siny)) 
(if (= lsx 6) 
(progn
(setq sinx (substr sinx 2 5))
(setq x (substr x 2 9))
(setq lsx 5)
)
)
(if (= lsy 6)
(progn
(setq siny (substr siny 2 5))
(setq y (substr y 2 9))
(setq lsy 5)
)
)
(setq flx (+ lsx 3))
(setq fly (+ lsy 3))
(setq llsx (+ 2 lsx))
(setq llsy (+ 2 lsy))
(setq rx (substr x llsx 3))
(setq ry (substr y llsy 3))
(setq cnt (1+ cnt))
(setq scnt (rtos cnt 2 0))
(setq lcnt (strlen scnt))
(if (= lcnt 1) (setq fcnt (strcat "11000" scnt "+0000000" scnt)))
(if (= lcnt 2) (setq fcnt (strcat "1100" scnt "+000000" scnt)))
(if (= lcnt 3) (setq fcnt (strcat "110" scnt "+00000" scnt)))
(princ fcnt i)
(princ " " i)
(if (= lsx 4) (setq fx (strcat "81..00+0" sinx rx)))
(if (= lsy 4) (setq fy (strcat "82..00+0" siny ry)))
(if (= lsx 5) (setq fx (strcat "81..00+" sinx rx)))
(if (= lsy 5) (setq fy (strcat "82..00+" siny ry)))
(if (= lsx 3) (setq fx (strcat "81..00+00" sinx rx)))
(if (= lsy 3) (setq fy (strcat "82..00+00" siny ry)))
(if (= lsx 2) (setq fx (strcat "81..00+000" sinx rx)))
(if (= lsy 2) (setq fy (strcat "82..00+000" siny ry)))
(if (= lsx 1) (setq fx (strcat "81..00+00000" sinx rx)))
(if (= lsy 1) (setq fy (strcat "82..00+00000" siny ry)))
(setq fz "83..00+00000000")
(princ fx i)
(princ " " i)
(princ fy i)
(princ " " i)
(princ fz i)
(princ "\n" i)
(command "osnap" "none")
(setq p2 (polar pnt 2.4 (* 1.25 ha)))
(command "text" "m" p2 ha 0 scnt)
)
(close i)
)
)
(if (/= pass 1001) (alert "  TO RUN THIS PROGRAM CORRECTLY \n    PLEASE CONTACT TEL  774700 \n         SAAD AL-KHATEEB"))
(command "osnap" "nod")
(princ)
)
