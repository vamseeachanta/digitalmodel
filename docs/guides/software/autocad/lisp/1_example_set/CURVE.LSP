(defun c:cur()
(command "osnap" "node")
(setq pt1 (getpoint"\nSELECT FIRST POINT:"))
(setq pt2 (getpoint"\nSELECT SECOND POINT:"))
(setq pt3 (getpoint"\nSELECT THIRD POINT:"))
(setq d1 (distance pt1 pt2))
(setq d2 (distance pt1 pt3))
(setq d3 (distance pt3 pt2))
(setq dd1 (/ d1 2))
(setq d4 (sqrt (- (* d3 d3) (* dd1 dd1))))
(setq ap1 (atan (/ d4 dd1)))
(setq ap2 (atan (/ dd1 d4)))
(setq aut (cos ap2))
(setq rad (/ dd1 aut))
(setq bea (angle pt1 pt2))
(setq ang (- bea ap2))
(setq ptc (polar pt1 ang rad))
(command "osnap" "none")
		(command "arc" "c" ptc pt2 pt1)
(setq d5 (sqrt (- (* rad rad) (* dd1 dd1))))
(setq h (- rad d5))
(princ "\nARC HIGHT IS: ")
(princ h)
(princ)
)
