(prompt "\nLOADING PROT.LSP PLEASE WAIT...")
(SETVAR "UCSICON" 0)
(SETVAR"CMDECHO" 0)
(SETVAR"BLIPMODE" 0)
(SETVAR"HIGHLIGHT" 1)
(SETVAR "MIRRTEXT" 0)
(defun c:c8()(command"chprop" pause "" "c" "8" "")(princ))
(defun c:cvv()
 (command "pedit" PAUSE "c" "")(princ))
(defun c:cvb()
 (command "pedit" PAUSE "o" "")(princ))
(DEFUN C:CPNT()
(COMMAND "LAYER" "S" "CVD-PTEL" "OF" "*" "" "ON" "CVD-PTEL,CVD-PTXT,CVD-CPNT" "")(PRINC))
(DEFUN C:GBLL()
 (COMMAND "INSERT" "*C:/ACAD12/GBLL" "INT" PAUSE "" "" "")
(PRINC))
(DEFUN C:GBRR()
 (COMMAND "INSERT" "*C:/ACAD12/GBRR" "INT" PAUSE "" "" "")
(PRINC))
(DEFUN C:GTLL()
 (COMMAND "INSERT" "*C:/ACAD12/GTLL" "INT" PAUSE "" "" "")
(PRINC))
(DEFUN C:GTRR()
 (COMMAND "INSERT" "*C:/ACAD12/GTRR" "INT" PAUSE "" "" "")
(PRINC))
(defun c:ce()
(setq soele(ssget))
(setq ele(getreal "\nEnter Elevation: "))
(command "change" soele "" "p" "e" ele "")
(princ))
(DEFUN C:LTP()
	(SETQ A(SSGET))
	(SETQ B(GETSTRING "\nCHOOSE YOUR LINETYPE : "))
	(COMMAND "CHPROP" A "" "LT" B "")(princ))
(DEFUN C:LISP()
	(setq a (getstring "\nEnter the name of lisp to load: "))
(setq a1(strcat "c:/acad12/support/" a))
(setq aa(strcat "c:/acad12/support/" a ".lsp"))
(setq a2(findfile aa))
(if (null a2)
(progn
	(Load a)))
(if a2
(PROGN
	(load a1)))(princ))
(DEFUN C:DDLISP()
	(setq a (getfiled "Select Lisp to load" "c:/acad12/support/" "lsp" 2))
(setq a1(strcat "c:/acad12/support/" a))
(setq aa(strcat "c:/acad12/support/" a ".lsp"))
(setq a2(findfile aa))
(if (null a2)
(progn
	(Load a)))
(if a2
(PROGN
	(load a1)))(princ))
(defun c:isbt ()
  (setq	a  (entget (car (entsel)))
	a2 (assoc 1 a)
	a1 (cdr a2)
	el (strlen a1)
	c  1
	n  ""
  )
  (while (<= c el)
    (setq n (strcat n (substr a1 c 1) " ")
	  c (+ 1 c)
    )
  )
  (setq addsp (cons 1 n))
  (if (= (cdr (assoc 0 a)) "TEXT")
    (progn
  (entmod (subst addsp a2 a))))
  (princ)
)
(DEFUN C:BPP()
		 (COMMAND "BREAK" PAUSE "F" PAUSE "@")(PRINC))
(DEFUN C:MBPP()
(setq sel(entsel))
		 (COMMAND "BREAK" sel "F" PAUSE "@")
(while (setq pt(getpoint "\nPick point to Break: "))
(command "break" sel "f" pt "@"))
(PRINC))
(DEFUN C:BSP()
		 (COMMAND "BREAK" PAUSE "@")(princ))
(DEFUN C:BB()
		 (COMMAND "BREAK" PAUSE "F" "INT" PAUSE "INT" PAUSE)(princ))
(DEFUN C:MM()
		 (COMMAND "BREAK" PAUSE "F" "MID" PAUSE "MID" PAUSE)(princ))
(DEFUN C:EE()
		 (COMMAND "BREAK" PAUSE "F" "END" PAUSE "END" PAUSE)(PRINC))
(DEFUN C:INT()
		 (COMMAND "BREAK" PAUSE "F" "INT" PAUSE "INT" PAUSE)(princ))
(DEFUN C:NEA()
		 (COMMAND "BREAK" PAUSE "F" "NEA" PAUSE PAUSE "")(princ))
(DEFUN C:EF()
		 (COMMAND "BREAK" PAUSE "F" "END" PAUSE PAUSE "")(princ))
(DEFUN C:@()
		 (SETVAR "CMDECHO" 0)(princ))
(DEFUN C:@1()
		 (SETVAR "CMDECHO" 1)(princ))
(defun c:cC()
(prompt "\nSelect the entities to change")
(setq a (ssget))
(setq b (acad_colordlg 256))
(command "chprop" a "" "C" b "")
(princ))
(DEFUN C:C1()
		 (SETQ A(SSGET))
		(COMMAND"CHPROP" A "" "C" "1" "")(princ))
(DEFUN C:C2()
		 (SETQ A(SSGET))
		(COMMAND"CHPROP" A "" "C" "2" "")(princ))
(DEFUN C:C3()
		 (SETQ A(SSGET))
		(COMMAND"CHPROP" A "" "C" "3" "")(princ))
(DEFUN C:C4()
		 (SETQ A(SSGET))
		(COMMAND"CHPROP" A "" "C" "4" "")(princ))
(DEFUN C:C5()
		 (SETQ A(SSGET))
		(COMMAND"CHPROP" A "" "C" "5" "")(princ))
(DEFUN C:C6()
		 (SETQ A(SSGET))
		(COMMAND"CHPROP" A "" "C" "6" "")(princ))
(DEFUN C:C7()
		 (SETQ A(SSGET))
		(COMMAND"CHPROP" A "" "C" "7" "")(princ))
(DEFUN C:C9()
		 (SETQ A(SSGET))
		(COMMAND"CHPROP" A "" "C" "9" "")(PRINC))
(DEFUN C:C10()
		 (SETQ A(SSGET))
		(COMMAND"CHPROP" A "" "C" "10" "")(PRINC))
(DEFUN C:C11()
		 (SETQ A(SSGET))
		(COMMAND "CHPROP" A "" "C" "11" "")(PRINC))
(DEFUN C:C12()
		 (SETQ A(SSGET))
		(COMMAND "CHPROP" A "" "C" "12" "")(PRINC))

(DEFUN C:C40()
		 (SETQ A(SSGET))
		(COMMAND "CHPROP" A "" "C" "40" "")(PRINC))
(DEFUN C:C202()
		 (SETQ A(SSGET))
		(COMMAND "CHPROP" A "" "C" "202" "")(PRINC))
(DEFUN C:C20()
		 (SETQ A(SSGET))
		(COMMAND "CHPROP" A "" "C" "20" "")(PRINC))
(DEFUN C:C156()
		 (SETQ A(SSGET))
		(COMMAND "CHPROP" A "" "C" "156" "")(PRINC))
(DEFUN C:C130()
		 (SETQ A(SSGET))
		(COMMAND "CHPROP" A "" "C" "130" "")(PRINC))
(DEFUN C:C255()
		 (SETQ A(SSGET))
		(COMMAND"CHPROP" A "" "C" "255" "")(princ))
(DEFUN C:CBY()
		 (SETQ A(SSGET))
		(COMMAND"CHPROP" A "" "C" "BYLAYER" "")(princ))
(defun c:chct()
(command "layer" "c" "14" "cvd-cont" "c" "16" "Cvd-cant,cvd-hvyl" "")(princ))
(defun c:ch30()
(command "layer" "c" "30" "cvd-cont,cvd-cant" "c" "110" "cvd-hvyl" "")(princ))
(defun c:ch46()
(command "layer" "c" "4" "*cvd-cont,*cvd-cant" "c" "6" "*cvd-hvyl" "")(princ))
(defun c:chc()
	(setq a(ssget))
	(setq b(getstring "\nENTER THE COLOUR NO.:"))
	(command "chprop" a "" "c" b "")
	(princ))
(DEFUN C:N()
  (SETQ A(SSGET))
  (COMMAND "CHPROP" A "" "LA" "TEXT" "")(princ))      
(DEFUN C:NL()
	(COMMAND "CHPROP"  "LA" "" "LA" "TEXT" "c" "BYLAYER" "")(princ))      
(DEFUN C:NP()
	(COMMAND "CHPROP"  "P" "" "LA" "TEXT" "c" "BYLAYER" "")(princ))
(DEFUN C:TXT()
  (SETQ A(SSGET))
  (COMMAND "CHPROP" A "" "LA" "TXT" "C" "BYLAYER" "")(princ))      
(DEFUN C:CLT()
	(SETQ A(SSGET))
	  (SETQ B(GETSTRING "\nNEW LAYER : "))
	  (SETQ C(GETSTRING "\nNEW COLOR : "))
	(SETQ D(GETSTRING "\nNEW LINETYPE : "))
		(COMMAND "CHPROP" A "" "LA" B "C" C "LT" D "")(princ))
(defun c:ze()(command "zoom" "e")(command "zoom" ".8x")
(if (= (getvar "ltscale") 1)
(progn 
(setvar "ltscale" 4)))
(princ))
(defun c:zx()(command "zoom" ".8x")(princ))
(defun c:zz()(command "zoom" "2x")(princ))
(defun c:zw()(command "zoom" "w")(princ))
(defun c:zd()(command "zoom" "d")(princ))
(defun c:zp()(command "zoom" "p")(princ))
(defun c:zc()(command "zoom" "c" "mid" pause "50")(princ))
(defun c:el()(command "erase" "l" "")(princ))
(defun c:ep()(command "erase" "p" "")(princ))
(defun c:ew()(command "erase" "w" pause pause "")(princ))
(defun c:ec()(command "erase" "c" pause pause "")(princ))
(defun c:es()(command "erase" "si")(princ))
(defun c:ml()(command "move" "l" "")(princ))
(defun c:mp()(command "move" "p" "")(princ))
(defun c:mw()(command "move" "w")(princ))
(defun c:mc()(command "move" "c")(princ))
(defun c:sc2()(command "scale" pause "" "ins" PAUSE "2")(princ))
(defun c:tmv()
	(setq a(ssget))
(command "move" a "" "ins" pause "per" pause)
(princ))
(defun c:s()
(SETVAR "CMDECHO" 0)
(SETQ A(GETVAR "DWGNAME"))
(PROMPT (STRCAT "\nSaving File to " a))
(command "qsave")
	(PROMPT "\nFILE SAVED.")
(princ))
(defun c:box()
(graphscr)
	  (setq fpt(getpoint "\nPICK FIRST CORNER OF BOX :")
		tpt(getcorner "\nPICK OPPOSITE CORNER OF BOX :" fpt)
			  spt(list (car tpt)(cadr fpt))
			  frpt(list (car fpt)(cadr tpt))
	)
	(command "pline" fpt spt tpt frpt "c")
	(princ)
)
;;;(defun c:r() 
;;; (setq ax (strcase (getstring"\nRealy you want to REDRAW<N> :")))
;;; (if (= AX "Y")
;;; (command"redraw")
;;;(prompt"\nPlease type `RR'to REDRAW"))(princ))
;;;(defun c:rr() (command"redraw")(princ))
(defun c:w()
	(SETVAR "CMDECHO" 0)
	(setq a(getreal "\nEnter New Width :"))
	(command "pedit" pause "w" a "")(PRINC))
(defun c:ww()(command "pedit" pause "W" "0" "")(princ))
(defun c:JC()
	(SETQ A(ENTSEL "\nPLEASE SELECT A POLYLINE :"))
		(command "PEDIT" A "J" "C" PAUSE PAUSE "" "")
	(princ)
)
(defun c:JP()
	(SETQ A(ENTSEL "\nPLEASE SELECT A POLYLINE :"))
		(command "PEDIT" A "J" "P" "" "")
	(princ)
)
(defun c:j()(command "pedit" pause "j" pause "" "")(PRINC))
(defun c:K()(command "pedit" pause "l" "on" "x")(princ))
(defun c:KF()(command "pedit" pause "l" "off" "x")(princ))
(defun c:ct()(command "change" pause "" "" "" "" "")(princ))
(defun c:ed()(command "pedit" pause "e"))
(defun c:chg()
	(setq a (ssget)
	 b (sslength a)
			c 0
			ol(getstring t "\nOld String: "))
	(if (/= ol "")
		(progn                     
			(setq ne(getstring t "\nNew String: ")
				 lo (strlen ol)
			)
		(while (< c b)
				(setq d (Entget(ssname a c)))
				(redraw (cdr(assoc -1 d)) 3)
				(if (= (cdr(assoc 0 d)) "TEXT")
					(progn
						(setq e (cdr(assoc 1 d))
								f (strlen e)
								g 1
								h ""
						)
						(while (<= g f)
					 (if (= (substr e g lo) ol)
								(progn
									(setq h (strcat h ne)
									 g (+ g lo))
								)
								(progn                    
									(Setq h (strcat h (substr e g 1))
									 g (+ 1 g))
								)        
							)
						)
						(setq d (subst (cons 1 h) (cons 1 e) d))
						(entmod d)
					)
				)
				(setq c (+ c 1))
			)
		)
	)               
	(princ)
)
;;;Changing the text height
(defun c:cth()
	(setq a (ssget)
			b1(getstring"\nEnter New text height: "))
	(if (= b1 "")
		(setq b (entget (car (entsel"\nWhich text to assine height: ")))
				b1 (cdr (assoc 40 b)))
		(SETQ B1 (ATOF B1))             
	)
	(setq   c (sslength a)
			d 0)
	(while (< d c)
(setq pr1 (entget(ssname a d))
		pr1 (subst (cons 40 b1) (cons 40 (cdr(assoc 40 pr1))) pr1)
)
		(entmod pr1)
		(setq d (1+ d))
	)       
	(princ)
)
;;;Changing the text Width
(defun c:ctw()
	(setq a (ssget)
		b1(getstring"\nEnter New text width: "))
	(if (= b1 "")
	(setq b (entget (car (entsel"\nWhich text to assine the width: ")))
	 b1 (cdr (assoc 41 b)))
	 (SETQ B1 (ATOF B1))             
	 )
	 (setq   c (sslength a)
  d 0)
	(while (< d c)
(setq pr1 (entget(ssname a d))
		pr1 (subst (cons 41 b1) (cons 41 (cdr(assoc 41 pr1))) pr1)
)
		(entmod pr1)
		(setq d (1+ d))
	)       
	(princ)
)
;;;Changing the text Style
(defun c:cts()
	(setq a (ssget)
			b1(getstring"\nEnter New text style: "))
	(if (= b1 "")
		(setq b (entget (car (entsel"\nWhich text to assine the style: ")))
				b1 (cdr (assoc 7 b)))
	)
	(setq   c (sslength a)
			d 0)
	(while (< d c)
(setq pr1 (entget(ssname a d))
		pr1 (subst (cons 7 b1) (cons 7 (cdr(assoc 7 pr1))) pr1)
)
		(entmod pr1)
		(setq d (1+ d))
	)
	(princ)
)
(DEFUN C:CNT()
(setq a(ssget))(command "chprop" a "" "lt" "continuous" "")(princ))
(defun c:edt()
	(SETQ OLD_OSNAP(GETVAR "OSMODE"))
                 (SETVAR "OSMODE" 512)
		 (setq a (ssget)
			b (sslength a)
		 c 0
                 pt(getpoint "\nPick Point on reference line: "))
                 (SETQ 
		 pt1(getpoint pt "\nPick Secon point: ")
	)
	 (SETVAR "OSMODE" OLD_OSNAP)
	 (while (< c b)
		(setq d (entget(ssname a c)))
	  (if (= (cdr(assoc 0 d)) "TEXT")
			(progn
			 (setq e (cdr(assoc 50 d))
		f (angle pt pt1)
		d (subst (cons 50 f) (cons 50 e) d)
	)
		(entmod d)
	)       
	 )
	  (setq c (+ 1 c))
	 )
	 (princ)
)
(defun c:mi()
	(setq a (getstring "\nEnter Block Name: ")
	 b (getpoint "\nEnter Block Position: "))
	(while (/= b nil)
		(command "insert" a b "" "" "")
		(setq b (getpoint "\nEnter Block Position: "))
		(if (= b nil)
	 (progn
		 (setq a (getstring "\nEnter Block Name: "))
		 (if (/= a "")
			 (setq b (getpoint "\nEnter Block Position: "))
			 (setq b nil)
		 )
	 )
		)
	)
	(princ)
)
(defun c:ls()
	 (setq a(getstring "\nEnter the layer name to set :"))
	 (command "layer" "s" a "")
	(princ)
)
(defun c:dsd()(command"chprop" pause "" "lt" "dashed" "")(princ))
(defun c:dsdx2()(command "chprop" pause "" "lt" "dashedx2" "")(princ))
(defun c:ddot()(command "chprop" pause "" "lt" "dashdot" "")(princ))
(defun c:ddotx2()(command "chprop" pause "" "lt" "dashdotx2" "")(princ))
(defun c:hid()(command"chprop" pause "" "lt" "hidden" "")(princ))
(defun c:cent()(command"chprop" pause "" "lt" "center" "")(princ))
(defun c:dot()(command"chprop" pause "" "lt" "dot" "")(princ))
(defun c:dotX2()(command"chprop" pause "" "lt" "dotX2" "")(princ))
(defun c:cont()(command"chprop" pause "" "lt" "continuous" "")(princ))
(defun c:phn()(command"chprop" pause "" "lt" "phantom" "")(princ))
(defun c:dsd2()(command"chprop" pause "" "lt" "dashed2" "")(princ))
(defun c:hid2()(command"chprop" pause "" "lt" "hidden2" "")(princ))
(defun c:dot2()(command"chprop" pause "" "lt" "dot2" "")(princ))
(defun c:div()(command"chprop" pause "" "lt" "divide" "")(princ))
(defun c:divx2()(command "chprop" pause "" "lt" "dividex2" "")(princ))
(defun c:bor()(command"chprop" pause "" "lt" "border" "")(princ))
(defun c:borx2()(command "chprop" pause "" "lt" "borderx2" "S" "1" "")(princ))
(defun c:phn2()(command"chprop" pause "" "lt" "phantom2" "")(princ))
(defun c:sc5()
	(setq a(ssget))
	(command "scale" a "" PAUSE "0.5")(princ))
(defun c:CP0()
	(setq a(ssget))
	(command "chprop" a "" "la" "0" "")(princ))
(defun c:rd()
	  (setq a(ssget))
	  (command "chprop" a "" "la" "road" "")(princ))
(defun c:pll()
	 (setq a(ssget))(command "chprop" a "" "la" "power" "")(princ))
(defun c:wat()
	 (setq a(ssget))(command "chprop" a "" "la" "water" "")(princ))
(defun c:sr()
	 (setq a(ssget))(command "chprop" a "" "la" "stream" "")(princ))
(defun c:ct()
	 (setq a(ssget))(command "chprop" a "" "la" "cont" "")(princ))
(defun c:ct1()
	 (setq a(ssget))(command "chprop" a "" "la" "cont1" "")(princ))
(defun c:cat()
	 (setq a(ssget))(command "chprop" a "" "la" "cont-alt" "")(princ))
(defun c:grd()
	 (setq a(ssget))(command "chprop" a "" "la" "grid" "")(princ))
(defun c:bld()
	 (setq a(ssget))(command "chprop" a "" "la" "building" "C" "BYLAYER" "")(princ))
(defun c:g()
	 (setq a(ssget))(command "chprop" a "" "la" "con-txt" "")(princ))
(defun c:g1()
	 (setq a(ssget))(command "chprop" a "" "la" "con-txt1" "")(princ))
(defun c:spt()
	 (setq a(ssget))(command "chprop" a "" "la" "sp-ht" "")(princ))
(defun c:tb()
	 (setq a(ssget))(command "chprop" a "" "la" "title" "")(princ))
(defun c:lard()
	 (command "layer" "s" "road" "")(princ))
(defun c:lact()
	 (command "layer" "s" "cont" "")(princ))
(defun c:lan()
	 (command "layer" "s" "text" "")(princ))
(defun c:bly()
	 (setq a(ssget))
	  (command "chprop" a "" "lt" "bylayer" "c" "bylayer" "")
 (princ)
)
(DEFUN C:ROB()
(COMMAND "ROTATE" "c" PAUSE PAUSE "" "ENDP" PAUSE "R" "@" "ENDP" PAUSE "0")
(COMMAND "MOVE" "P" "" "@")(PRINC))
(DEFUN C:ROA()
(COMMAND "ROTATE" "ALL" "" "0,0,0" "R" PAUSE PAUSE "0")(PRINC))
(defun c:sby()
	(command "linetype" "s" "bylayer" "")(princ))
(DEFUN C:H3()
	(COMMAND "HATCH" "U" "NEA" PAUSE "NEA" PAUSE  PAUSE "N")(PRINC))

(DEFUN C:HD()
	(COMMAND "HATCH" "DOTS, N" "4" "E" PAUSE "")(PRINC))
(DEFUN C:HS()
	(COMMAND "HATCH" "SOLID" PAUSE "")(PRINC))
(DEFUN C:HDH()
	(COMMAND "HATCH" "DASH" "5" "E" PAUSE "")(PRINC))
(DEFUN C:NP()
(COMMAND "LAYER" "S" "N-PNT" "C" "210" "N-PNT" "OFF" "*" "" "")
(COMMAND "LAYER" "ON" "N-PNT" "")(PRINC))
(defun c:indx()
(setq pt(getpoint "\nPick point: "))
(setq ptc(list (- (car pt) 28.523) (- (cadr pt) 417.297)))
(setq val(getreal "\nEnter sheet no: "))
(setq value(strcat "SHEET NO. " (rtos val 2 0) " OF 38"))
(command "insert" "*c:/toshiba/final/mainplt/indx" pt "" "")
(command "zoom" "c" ptc "100")
(COMMAND "change" pause "" "" "" "" "" value)
(c:zp)
(c:hbx)
(princ))
(defun c:hbx()
(setq pt1(getpoint "\nPick first point: "))
(setq pt3(getcorner pt1 "\nPick second point: "))
(setq pt2(list (car pt3) (cadr pt1)))
(setq pt4(list (car pt1) (cadr pt3)))
(command "pline" pt1 pt2 pt3 pt4 "c")
(setq sella(entlast))
(command "hatch" "u" "45" "1" "n" "la" pause "")
(command "chprop" "la" "" "la" "grid" "c" "4" "")
(command "erase" sella "")(princ))
(defun c:MX()
(setq smx(ssget))
(setq oso(getvar "osmode"))
(setvar "osmode" 64)
(setq ptf(getpoint "\nPick base point: "))
(setq pts(getpoint "\nPick X point: "))
(setvar "osmode" oso)
(setq ptfin(list (car pts) (cadr ptf)))
(command "move" smx "" ptf ptfin)(princ))
(DEFUN C:IRW()
(COMMAND "INSERT" "*C:/TOSHIBA/RAW-PIP" "ENDP" PAUSE "" "")(PRINC))
(DEFUN C:CVF()
(COMMAND "LAYER" "F" "CVD-PTEL,CVD-PTXT,CVD-CPNT" "")(PRINC))
(DEFUN C:FVP()
(COMMAND "VPOINT" "0,-1,0")(PRINC))
(DEFUN C:NVP()
(COMMAND "VPOINT" "0,0,1")(PRINC))
(DEFUN C:IT()
(COMMAND "INSERT" "*C:/DAMAN/SIL_LS/LSCH" "-800,75" "" "")
(COMMAND "INSERT" "*C:/DAMAN/SIL_LS/LST" PAUSE "" "")
(COMMAND "DDEDIT" "L" "")(PRINC))
(defun c:plt()
(command "layer" "c" "2" "umr" "f" "cvd-cpnt,cvd-ptxt" "")(princ))
(defun c:BG()
(setq laold(getvar "clayer"))
(setvar "clayer" "jc01")
(setq osold(getvar "osmode"))
(setq os(setvar "osmode" 8))
(setq a(getpoint "\nPick nod point: "))
(setq b(getpoint a "\nPick other point: "))
(setq os1(setvar "osmode" os))
 (command "3DPOLY" A B "")
 (command "CHPROP" "L" "" "LA" "JC01" "")
 (command "INSERT" "*BRG" a "" b)
 (command "LAYER" "OFF" "CVD*" "")
  (command "LAYER" "ON" "JC01" "")
 (command "STRETCH" "L" "W" PAUSE PAUSE "" "ENDP" PAUSE B)
 (command "LAYER" "ON" "CVD*" "")
(setvar "clayer" laold)
 (princ))
(defun c:if()
(command "-image" "u" "*")(princ))
(defun c:ion()
(command "-image" "r" "*")(princ))
(DEFUN C:MLF()
(COMMAND "LAYER" "OFF" "*" "N" "ON" "BLOCK-BOUNDARY,*BLOCK-NO,WARD-BOUNDARY,WARD-NO" "")(PRINC))
(DEFUN C:MLN()
(COMMAND "LAYER" "ON" "*" "OFF" "IMAGE,ERROR" "")(PRINC))
(DEFUN C:PUA()
(COMMAND "PURGE" "ALL" "*" "N")(PRINC))
(DEFUN C:DLE()
(SETVAR "DIMASZ" 1.8)
;(SETVAR "CLAYER" "TEXT")
(COMMAND "DIM" "LE" PAUSE PAUSE ^C "E")
(PRINC))
(defun c:POR()
(command "insert" "//Theovel18/d/DALLAL-CADASTRAL/NEW-SEPERATE/FIN-BLOCKS/POTRAIT" pause "" "" "")(princ))
(defun c:LAND()
(command "insert" "//Theovel18/d/DALLAL-CADASTRAL/NEW-SEPERATE/FIN-BLOCKS/LANDSCAPE" pause "" "" "")(princ))
(defun c:mangarx()
  (arxload "doslib14_tv")
  (arxload "sheetmaker")
(load "mcs")
  (princ))
(defun c:unarx()
  (arxunload "doslib14_tv")
  (arxunload "sheetmaker")(princ))
(defun c:lmm()
	(command "line" (getvar "extmin") (getvar "extmax") "")(PRINC))
(defun c:sep()
(setq sel(ssget))
(setq ascode(getint "\nEnter Associative Code/<Object Name (0)>: "))
(if (NULL ascode)
(setq ascode 0))
(setq filent(getstring T "\nFilter Entity: "))
(setq selent(ssget "p"(list (cons ascode filent))))
(command "select" selent "")(princ))
(DEFUN C:FF()
(COMMAND "IMAGEFRAME" "OFF"))
