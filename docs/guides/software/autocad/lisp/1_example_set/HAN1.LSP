; 11/05/2000
(defun c:DH ();(kieu)
 (SETVAR "OSMODE" 179)
 (initget 7)
 (setq pt1 (getpoint "Cho diem dau: "))
 (setq pt2 (getpoint pt1 "\nCho diem cuoi: "))
 (SETVAR "OSMODE" 0)
 (if (null h_wid) (setq h_wid 1.0))
 (initget 6)
 (setq _h_wid (getreal (strcat "\nChieu rong moi han <" (rtos h_wid 2 1) ">: ")))
 (if (/= _h_wid nil) (setq h_wid _h_wid))
 (initget "Trai Phai")
 (setq typ (getkword "Moi han ben Trai/<Phai>: "))
 (setq alp (angle pt1 pt2)
	len (distance pt1 pt2)
	px (car pt1)
	py (cadr pt1)
	count 0
	ntimes (fix (/ len h_wid))
	dx (/ (- (car pt2) px) ntimes)
	dy (/ (- (cadr pt2) py) ntimes)
	mbloc (ssadd)
	tt 1
	pt pt1
 )
 (repeat (1+ ntimes)
  (if (= typ "Trai")
   (setq pt2 (polar pt1 (+ alp (/ pi 2)) h_wid))
   (setq pt2 (polar pt1 (- alp (/ pi 2)) h_wid))
  )
  (setq _pt1 (list (+ px (* dx 0.8)) (+ py (* dy 0.8)))
	_pt2 (list (+ (car pt2) (* dx 0.8)) (+ (cadr pt2) (* dy 0.8)))
  )
  (command "LINE" pt1 pt2 "")
  (ssadd (entlast) mbloc)
  (setq px (+ px dx)
	py (+ py dy)
	pt1 (list px py)
	count (1+ count)
  )
 )
 (while (tblsearch "BLOCK" (setq bl_name (strcat "HAN" (itoa tt))))
	(setq tt (1+ tt))
 )
 (SETVAR "OSMODE" 179)
 (command "BLOCK" bl_name pt mbloc "" "INSERT" bl_name pt "" "" "")
 (_restore)
 (princ)
)

(defun c:D2 ();(kieu)
 (SETVAR "OSMODE" 179)
 (initget 7)
 (setq pt1 (getpoint "Cho diem dau: "))
 (setq pt2 (getpoint pt1 "\nCho diem cuoi: "))
 (SETVAR "OSMODE" 0)
 (if (null h_wid) (setq h_wid 1.0))
 (initget 6)
 (setq _h_wid (getreal (strcat "\nChieu rong moi han <" (rtos h_wid 2 1) ">: ")))
 (if (/= _h_wid nil) (setq h_wid _h_wid))
 (initget "Trai Phai")
 (setq typ (getkword "Moi han ben Trai/<Phai>: "))
 (setq alp (angle pt1 pt2)
	len (distance pt1 pt2)
	px (car pt1)
	py (cadr pt1)
	count 0
	ntimes (fix (/ len h_wid))
	dx (/ (- (car pt2) px) ntimes)
	dy (/ (- (cadr pt2) py) ntimes)
	mbloc (ssadd)
	tt 1
	pt pt1
 )
 (repeat (1+ ntimes)
  (if (= typ "Trai")
   (setq pt2 (polar pt1 (+ alp (/ pi 2)) h_wid))
   (setq pt2 (polar pt1 (- alp (/ pi 2)) h_wid))
  )
  (setq _pt1 (list (+ px (* dx 0.8)) (+ py (* dy 0.8)))
	_pt2 (list (+ (car pt2) (* dx 0.8)) (+ (cadr pt2) (* dy 0.8)))
  )

  ( if (< (rem count 6) 4)
    (command "LINE" pt1 pt2 ""))

  (ssadd (entlast) mbloc)
  (setq px (+ px dx)
	py (+ py dy)
	pt1 (list px py)
	count (1+ count)
  )
 )
 (while (tblsearch "BLOCK" (setq bl_name (strcat "HAN" (itoa tt))))
	(setq tt (1+ tt))
 )
 (SETVAR "OSMODE" 179)
 (command "BLOCK" bl_name pt mbloc "" "INSERT" bl_name pt "" "" "")
 (_restore)
 (princ)
)

(defun c:D3 ();(kieu)
 (SETVAR "OSMODE" 179)
 (initget 7)
 (setq pt1 (getpoint "Cho diem dau: "))
 (setq pt2 (getpoint pt1 "\nCho diem cuoi: "))
 (SETVAR "OSMODE" 0)
 (if (null h_wid) (setq h_wid 1.0))
 (initget 6)
 (setq _h_wid (getreal (strcat "\nChieu rong moi han <" (rtos h_wid 2 1) ">: ")))
 (if (/= _h_wid nil) (setq h_wid _h_wid))
 (initget "Trai Phai")
 (setq typ (getkword "Moi han ben Trai/<Phai>: "))
 (setq alp (angle pt1 pt2)
	len (distance pt1 pt2)
	px (car pt1)
	py (cadr pt1)
	count 0
	ntimes (fix (/ len h_wid))
	dx (/ (- (car pt2) px) ntimes)
	dy (/ (- (cadr pt2) py) ntimes)
	mbloc (ssadd)
	tt 1
	pt pt1
 )
 (repeat (1+ ntimes)
  (if (= typ "Trai")
   (setq pt2 (polar pt1 (+ alp (/ pi 2)) h_wid))
   (setq pt2 (polar pt1 (- alp (/ pi 2)) h_wid))
  )
  (setq _pt1 (list (+ px (* dx 0.8)) (+ py (* dy 0.8)))
	_pt2 (list (+ (car pt2) (* dx 0.8)) (+ (cadr pt2) (* dy 0.8)))
  )

   (if (/= count ntimes)
    (progn
     (command "LINE" pt1 _pt2 "")
     (ssadd (entlast) mbloc)
     (command "LINE" pt2 _pt1 "")
    )
   )
  
  (ssadd (entlast) mbloc)
  (setq px (+ px dx)
	py (+ py dy)
	pt1 (list px py)
	count (1+ count)
  )
 )
 (while (tblsearch "BLOCK" (setq bl_name (strcat "HAN" (itoa tt))))
	(setq tt (1+ tt))
 )
 (SETVAR "OSMODE" 179)
 (command "BLOCK" bl_name pt mbloc "" "INSERT" bl_name pt "" "" "")
 (_restore)
 (princ)
)

(defun c:D4 ();(kieu)
 (SETVAR "OSMODE" 179)
 (initget 7)
 (setq pt1 (getpoint "Cho diem dau: "))
 (setq pt2 (getpoint pt1 "\nCho diem cuoi: "))
 (SETVAR "OSMODE" 0)
 (if (null h_wid) (setq h_wid 1.0))
 (initget 6)
 (setq _h_wid (getreal (strcat "\nChieu rong moi han <" (rtos h_wid 2 1) ">: ")))
 (if (/= _h_wid nil) (setq h_wid _h_wid))
 (initget "Trai Phai")
 (setq typ (getkword "Moi han ben Trai/<Phai>: "))
 (setq alp (angle pt1 pt2)
	len (distance pt1 pt2)
	px (car pt1)
	py (cadr pt1)
	count 0
	ntimes (fix (/ len h_wid))
	dx (/ (- (car pt2) px) ntimes)
	dy (/ (- (cadr pt2) py) ntimes)
	mbloc (ssadd)
	tt 1
	pt pt1
 )
 (repeat (1+ ntimes)
  (if (= typ "Trai")
   (setq pt2 (polar pt1 (+ alp (/ pi 2)) h_wid))
   (setq pt2 (polar pt1 (- alp (/ pi 2)) h_wid))
  )
  (setq _pt1 (list (+ px (* dx 0.8)) (+ py (* dy 0.8)))
	_pt2 (list (+ (car pt2) (* dx 0.8)) (+ (cadr pt2) (* dy 0.8)))
  )

   (if (and (< (rem count 6) 4) (/= count ntimes))
     (progn	
      (command "LINE" pt1 _pt2 "")
      (ssadd (entlast) mbloc)
      (command "LINE" pt2 _pt1 "")
     )
   )

  (ssadd (entlast) mbloc)
  (setq px (+ px dx)
	py (+ py dy)
	pt1 (list px py)
	count (1+ count)
  )
 )
 (while (tblsearch "BLOCK" (setq bl_name (strcat "HAN" (itoa tt))))
	(setq tt (1+ tt))
 )
 (SETVAR "OSMODE" 179)
 (command "BLOCK" bl_name pt mbloc "" "INSERT" bl_name pt "" "" "")
 (_restore)
 (princ)
)
