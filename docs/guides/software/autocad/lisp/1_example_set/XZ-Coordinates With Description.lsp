;load program then enter XZ at command line
(defun c:XZ (/)
(setq obm (getvar "blipmode")) 
(setq oom (getvar "osmode"))
  (setq andr(getvar"angdir"))
 (setvar "angdir"1)
 (setq andb(getvar"angbase")) 
(setvar "angbase"(/ pi 2))
(setq aunt(getvar"aunits"))  
(setvar "aunits"2)
  (setvar "dimaunit"2)
  (setvar"dimadec"4)
  
(while
    (setq osmd (getvar "osmode"))
    (initget 1)
    (setq px (getpoint "\n click the point "))
    (setq osmd (getvar "osmode"))
    (initget 1)
    (setq pt (getpoint px "\n click for place for writing"))
    (setq y (cadr px))
    (setq x (car px))
    (setq z(last px))
  (if(null z)
    (setq z z))
(setq CH (getstring 1"\n CHAINAGE:"))
  (setvar "osmode"0)
    (setvar"textstyle" "standard")
        (setq dscrp (getstring 1"\n description of the point(press enter for nothing):"))
    (command "_qleader" px pt""""CH (strcat"E:"(rtos x 2 3 ))
	     (strcat"N:"(rtos y 2 3 )) dscrp"" "")
  (setq tds(entlast))
(if (null sca)
      (setq sca 1)
      )
    (initget 6)
    (setq scan (getreal (strcat"\n enter scale factor<"(rtos sca 2 3)">:")))
    (if scan(setq sca scan))
  (command"scale"tds"" pt sca) 
  (setvar"angbase"andb)
  (setvar "angdir"andr)
  (setvar"aunits"aunt)
  (setvar"osmode"osmd)
  
    )
      )
