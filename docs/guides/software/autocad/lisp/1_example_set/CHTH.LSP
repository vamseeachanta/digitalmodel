(Defun c:CTH (/ a)
   (setq olderr *error* *error* myerror)
   (setq ocmd (getvar "cmdecho"))
   (setq oblp (getvar "blipmode"))
   (setvar "cmdecho" 0)
   (setq a (ssget) thickness (getstring "\nChange to new Thickness: "))
   (command "CHPROP" a "" "T" thickness "")
   (setvar "cmdecho" ocmd)
   (setvar "blipmode" oblp)
   (setq *error* olderr)
   (princ))
