;================================================================================
;
;                            BONJOUR TOUT LE MONDE !
;                         THAN AI CHAO CAC BAN !
;
;   C'est la progame ACAD.lSP pour moi. Mais la prennent ! Bonne Heureu !
;
;   Day la chuong trinh ACAD.LSP moi nhat cua toi.Cac ban cu su dung vo tu
;  va sua chua theo so thich. Co gi can giai dap xin lien he :
                                                 LE ANH DUNG
;                                                Tel: 9762092
;                    Good Succes !
;===============================================================================
;============================= Dat cac bien so =================================
(setvar "pickbox" 5) (setvar "aperture" 5) (setvar "gripsize" 7) (setvar "blipmode" 0)
(setvar "savetime" 2) (setvar "mirrtext" 0) (setvar "tracewid" 200)
(setvar "surftab1" 16) (setvar "surftab2" 24)
;;; =============================== STATUS =================================
(setvar "modemacro"
 (strcat
    "Time:$(substr,$(getvar,cdate),10,2)" ":$(substr,$(getvar,cdate),12,2)"
    " <$(IF,$(>,$(strlen,$(GETVAR,dwgname)),18),$(substr,$(getvar,dwgname),$(-,$(strlen,$(GETVAR,dwgname)),17),18),$(getvar,dwgname), )" ">"
    "  $(substr,$(getvar,clayer),1,12)"
      " T:$(substr,$(getvar,thickness),1,8)"
      " W:$(substr,$(getvar,plinewid),1,8)"
      " U:$(substr,$(getvar,ucsname),1,8)"
      " C:$(substr,$(getvar,cecolor),1,3)"
      "$(IF,$(GETVAR,ORTHOMODE),_O, )"
      "$(if,$(getvar,snapmode),_S, )" ))        
;;;; ================== CAC FUNCTIONS DUNG TRONG ACAD.LSP =================
;     ====================== Tao & dat mau layer hien hanh ================
(defun taolop (mau lop / a) (setq a (tblsearch "layer" lop))
 (if (null a) (command "layer" "n" lop "c" mau lop "")) (setvar "clayer" lop)
 (princ "\n  Layer_ hien hanh la:  ") (princ lop)
 (princ "\n  Color layer_ hien hanh la:  ") (princ mau) (princ) )
;; ================ Change width of polylines =========================
(DEFUN wpline (pw)
(PRINC "\n         Chon doi tuong can thay doi do day (Width) = ")  (princ wid)
 (setq b (ssget)) 
 (setq sophantu (sslength b)) 
 (setvar "cmdecho" 0)
 (setq sodem 0) 
 (repeat sophantu
  (setq a (ssname b sodem))
  (setq list1 (assoc 0 (entget a)))
    (cond
     ((= (cdr list1) "POLYLINE") (command "_Pedit" a "w" wid ""))
     (PROGN (command "_Pedit" a "" "w" wid ""))    ) 
 (setq sodem (1+ sodem)) )(SETVAR "cmdecho" 1)(princ))
;  ========================= change thickness ===========================
(defun docao ( T)
   (princ "\nChon doi tuong can thay doi do cao (Thickness) = ") (princ T)
   (setq a(ssget)) (command "chprop" a "" "t" T "") (princ) )
;  ========================= change thickness ===========================
(defun caodo ( E )
   (princ "\nChon doi tuong can thay doi cao do (Elevantation) = ") (princ E)
   (setq a(ssget)) (command "change" a "" "p" "e" E "") (princ) )
;;; ========================= Quay goc theo goc =========================
(defun quaygoc ( g) (princ "\nChon doi tuong quay goc :") (princ g)
  (setq a(ssget))   (princ "\nChon diem goc de quay :")
                    (command "rotate" a "" pause g) (princ))
;;; ========================== Doi mau doi tuong =========================
(defun doimau ( m) (princ "\nChon doi tuong can doi sang mau :") (princ m)
                    (setq a(ssget))
                    (command "chprop" a "" "c" m "") (princ))
;;; ================================ Funtion-Dulieu =================================
(defun ha:nhap (kytu thamso) (princ kytu) (princ thamso) (princ ">: ") (setq key (getint)) (if key (setq thamso key)) (princ thamso) )
(defun ha:thoat () (reinit) (setq Temp "Da thoat khoi chuong trinh"))
(defun khoangcach (kh khq11 khq12 / h0 h1) (setq h1 (polar kh (angle '(0 0) (vectophap khq11 khq12)) 500)) (setq h0 (inters khq11 khq12 kh h1 nil)) (distance kh h0))
(defun hacat (hacat1 hacat2 / hacat3 chon) (if (and (/= hacat1 nil) (/= hacat2 nil)) (progn   (setq hacat3 (polar hacat1 (angle hacat1 hacat2) (/ (distance hacat1 hacat2) 2)))   (setq chon (ssget hacat3))   (command "break" chon hacat1 hacat2)  ) ) (princ) )
(defun hauon (hauon1 hauon2) (command "fillet" hauon1 hauon2))
(defun init () (setvar "blipmode" 0) (setvar "cmdecho" 0) (setvar "angbase" 0))
(defun reinit () (setvar "cmdecho" 1) (setvar "osmode" 0))
(defun tichvecto (vecto1 vecto2) (apply '+ (mapcar '* vecto1 vecto2)))
(defun vectophap (v01 v02 / vectochiphuong) (setq vectochiphuong (mapcar '- v01 v02)) (list (cadr vectochiphuong) (* -1 (car vectochiphuong))))
(defun ha:giaodiem (dc1 p1 p2 / hc hc1 diem1) (setq diem1 (vectophap p1 p2)) (setq hc1 (polar dc1 (angle '(0.0 0.0) diem1) 100)) (setq hc (inters p1 p2 dc1 hc1 nil)))
(defun dtr (dtr) (* pi (/ dtr 180.0)))
(defun rtd (rtd) (* 180.0 (/ rtd pi)))
;  =========================================================================
;;; ===========================  Cac Lenh Tat ==============================
(defun c:1()(setvar "cmdecho" 0) (command "color" "1")(princ))
(defun c:2()(setvar "cmdecho" 0) (command "color" "2")(princ))
(defun c:3()(setvar "cmdecho" 0) (command "color" "3")(princ))
(defun c:4()(setvar "cmdecho" 0) (command "color" "4")(princ))
(defun c:5()(setvar "cmdecho" 0) (command "color" "5")(princ))
(defun c:6()(setvar "cmdecho" 0) (command "color" "6")(princ))
(defun c:7()(setvar "cmdecho" 0) (command "color" "7")(princ))
(defun c:8()(setvar "cmdecho" 0) (command "color" "8")(princ))
(defun c:9()(setvar "cmdecho" 0) (command "color" "9")(princ))
(defun c:cb()(setvar "cmdecho" 0) (command "color" "bylayer")(princ))
(DEFUN C:3M  () (COMMAND "3MESH"))
(DEFUN C:A3  () (COMMAND "3DARRAY"))
(DEFUN C:AR  () (COMMAND "ARRAY"))
(DEFUN C:A   () (COMMAND "ARC"))
(DEFUN C:AAR () (COMMAND "APERTURE"))
(DEFUN C:AC  () (COMMAND "ARC"))
(DEFUN C:AG  () (COMMAND "DIM1" "ANGULAR"))
(DEFUN C:AT  ()   (princ "\nChon doi tuong ARRAY theo duong tron :") (setq a(ssget ))                  (COMMAND "ARRAY" a "" "P"))
(DEFUN C:AV  ()   (princ "\nChon doi tuong ARRAY theo hang_day vuong :") (setq a(ssget ))                  (COMMAND "ARRAY" a "" "R"))
(DEFUN C:AU  () (COMMAND "AUDIT" "Y" "") (COMMAND "QSAVE"))
(DEFUN C:ATF () (COMMAND "ATTDEF"))
(DEFUN C:DAT () (COMMAND "DDATTE"))
(DEFUN C:ATE () (COMMAND "ATTEDIT"))
(DEFUN C:ATX () (COMMAND "ATTEXT"))
(DEFUN C:B1  () (COMMAND "SETVAR" "PICKBOX" "1"))
(DEFUN C:B2  () (COMMAND "SETVAR" "PICKBOX" "2"))
(DEFUN C:B3  () (COMMAND "SETVAR" "PICKBOX" "3"))
(DEFUN C:B4  () (COMMAND "SETVAR" "PICKBOX" "4"))
(DEFUN C:B5  () (COMMAND "SETVAR" "PICKBOX" "5"))
(DEFUN C:B6  () (COMMAND "SETVAR" "PICKBOX" "6"))
(DEFUN C:B7  () (COMMAND "SETVAR" "PICKBOX" "7"))
(DEFUN C:B8  () (COMMAND "SETVAR" "PICKBOX" "8"))
(DEFUN C:B9  () (COMMAND "SETVAR" "PICKBOX" "9"))
(DEFUN C:BL  () (COMMAND "BLOCK"))
(DEFUN C:BM  () (COMMAND "BLIPMODE" "off"))
(DEFUN C:BMM () (COMMAND "BLIPMODE" "on"))
(DEFUN C:B   () (COMMAND "BREAK"))
(DEFUN C:BK  () (COMMAND "BREAK" PAUSE "FIRST"))
(defun c:BR  () (setvar "osmode" 32)   (command "break" pause "f" "int" pause  "@")   (setvar "osmode"  0))
(DEFUN C:CF  () (COMMAND "CHAMFER"))
(DEFUN C:CCF () (COMMAND "CHAMFER" "D"))
(DEFUN C:CFD () (COMMAND "CHAMFER" "D"))
(DEFUN C:D0  () (COMMAND "DONUT" "0"))
(DEFUN C:CI  () (COMMAND "CIRCLE"))
(DEFUN C:C   () (setvar "cmdecho" 1) (setq a (ssget)) (command "copy" a "" "m" pause) (princ))
(DEFUN C:CL  () (COMMAND "COPY" "L" "" "L" ""))
(DEFUN C:CP  () (COMMAND "COPY" "P" "" "P" ""))
(DEFUN C:D   () (COMMAND "DDEDIT"))
(defun c:DED () (command "dim1" "tedit"))
(DEFUN C:DA  () (setvar "cmdecho" 1) (setq ldim (tblsearch "layer" "dim")) (if (null ldim) (command "layer" "n" "DIM" "c" 9 "DIM" "")) (COMMAND "dim1" "aligned") (command "change" "last" "" "p" "la" "dim" "") (princ))
(DEFUN C:DB  () (setvar "cmdecho" 1) (setq ldim (tblsearch "layer" "dim")) (if (null ldim) (command "layer" "n" "DIM" "c" 9 "DIM" "")) (COMMAND "dim1" "baseline") (command "change" "last" "" "p" "la" "dim" "") (princ))
(DEFUN C:DS  () (COMMAND "DIST"))
(DEFUN C:DG  () (setvar "cmdecho" 1) (setq ldim (tblsearch "layer" "dim")) (if (null ldim) (command "layer" "n" "DIM" "c" 9 "DIM" "")) (COMMAND "dim1" "ang") (command "change" "last" "" "p" "la" "dim" "") (princ))
(DEFUN C:DI  () (setvar "cmdecho" 1) (setq ldim (tblsearch "layer" "dim")) (if (null ldim) (command "layer" "n" "DIM" "c" 9 "DIM" "")) (COMMAND "dim1" "dia") (command "change" "last" "" "p" "la" "dim" "") (princ))
(DEFUN C:DR  () (setvar "cmdecho" 1) (setq ldim (tblsearch "layer" "dim")) (if (null ldim) (command "layer" "n" "DIM" "c" 9 "DIM" "")) (COMMAND "dim1" "rad") (command "change" "last" "" "p" "la" "dim" "") (princ))
(DEFUN C:DH  () (setvar "cmdecho" 1) (setq ldim (tblsearch "layer" "dim")) (if (null ldim) (command "layer" "n" "DIM" "c" 9 "DIM" "")) (COMMAND "dim1" "hor") (command "change" "last" "" "p" "la" "dim" "") (princ))
(DEFUN C:DV  () (setvar "cmdecho" 1) (setq ldim (tblsearch "layer" "dim")) (if (null ldim) (command "layer" "n" "DIM" "c" 9 "DIM" "")) (COMMAND "dim1" "ver") (command "change" "last" "" "p" "la" "dim" "") (princ))
(DEFUN C:LD  () (setvar "cmdecho" 1) (setq ldim (tblsearch "layer" "dim")) (if (null ldim) (command "layer" "n" "DIM" "c" 9 "DIM" "")) (COMMAND "dim1" "lea") (command "change" "last" "" "p" "la" "dim" "") (princ))
(DEFUN C:DC  (/ pt a vonglap) (setq a (getvar "clayer")) (taolop 9 "dim")  (setq vonglap "T") (while (= vonglap "T")  (setq pt (getpoint "\nPlease pick a point "))  (if (null pt) (setq vonglap nil)  (command "dim1" "continue" pt "")  ) ) (setvar "clayer" a) (princ))
(DEFUN C:DN  () (COMMAND "DIM1" "NEWTEXT"))
(DEFUN C:Dtt  () (COMMAND "dtext"))
(DEFUN C:DE  () (COMMAND "DDEMODES"))
(DEFUN C:DDR () (COMMAND "DDRMODES"))
(DEFUN C:DDV () (COMMAND "DVIEW"))
(DEFUN C:DCA () (COMMAND "DVIEW" "all" "" "CA"))
(DEFUN C:DPA () (COMMAND "DVIEW" "all" "" "PA"))
(DEFUN C:DPO () (COMMAND "DVIEW" "all" "" "PO"))
(DEFUN C:DDD () (COMMAND "DVIEW" "all" "" "D"))
(DEFUN C:DZ  () (COMMAND "DVIEW" "all" "" "Z"))
(DEFUN C:ELP () (COMMAND "ELIPSE"))
(DEFUN C:EG  () (COMMAND "EDGE"))
(DEFUN C:E   () (COMMAND "ERASE"))
(DEFUN C:Ed  () (COMMAND "Edit"))
(DEFUN C:Eda () (COMMAND "Edit" "acad.lsp"))
(defun c:ew  () (command "erase" "wp"))
(defun c:ea  () (command "erase" "all"))
(defun c:EL  () (command "erase" "LAST"))
(defun c:EP  () (command "erase" "Previous"))
(defun c:ec  () (command "erase" "cp"))
(defun c:ef  () (command "erase" "f"))
(DEFUN C:ES  () (COMMAND "ERASE" "SINGLE"))
(DEFUN C:EP  () (COMMAND "ERASE" "PREVIOUS"))
(DEFUN C:EX  () (COMMAND "EXPLODE"))
(DEFUN C:ET  () (COMMAND "EXTEND"))
(DEFUN C:FS  () (COMMAND "FILES"))
(DEFUN C:FL  () (COMMAND "FILL"))
(DEFUN C:FF  () (COMMAND "FILLET" "R"))
(DEFUN C:F   () (COMMAND "FILLET"))
(DEFUN C:HD  () (COMMAND "HIDE"))
(DEFUN C:J   () (COMMAND "PEDIT" PAUSE "J"))
(DEFUN C:JJ  () (COMMAND "PEDIT" PAUSE "" "J"))
(DEFUN C:I   () (COMMAND "INSERT"))
(DEFUN C:ID  () (COMMAND "DDINSERT"))
(DEFUN C:L   () (COMMAND "LINE"))
(DEFUN C:LA  () (COMMAND "LAYER"))
(DEFUN C:LS  () (COMMAND "LIST"))
(DEFUN C:LI  () (COMMAND "LIST"))
(DEFUN C:LTS () (COMMAND "LTSCALE"))
(defun c:MA  () (command "move" "all"))
(DEFUN C:MB  () (COMMAND "PLAN" ""))
(DEFUN C:MD  () (COMMAND "VPOINT" "0.0,-1.0,0.0"))
(DEFUN C:MDT () (COMMAND "VPOINT" "-1.0,0.0,0.0"))
(DEFUN C:MDP () (COMMAND "VPOINT" "1.0,0.0,0.0"))
(DEFUN C:MDS () (COMMAND "VPOINT" "0.0,1.0,0.0"))
(DEFUN C:MT  () (COMMAND "MINSERT"))
(DEFUN C:MI  () (COMMAND "MIRROR"))
(DEFUN C:M   () (COMMAND "MOVE"))
(DEFUN C:ML  () (COMMAND "MOVE" "L"))
(DEFUN C:MP  () (COMMAND "MOVE" "P"))
(DEFUN C:O   () (COMMAND "OFFSET"))
(DEFUN C:OO  () (COMMAND "OOPS"))
(DEFUN C:OC  () (COMMAND "OSNAP" "CENT"))
(DEFUN C:OE  () (COMMAND "OSNAP" "ENDP"))
(DEFUN C:OS  () (COMMAND "OSNAP" "INSERT"))
(DEFUN C:OI  () (COMMAND "OSNAP" "INTER"))
(DEFUN C:OM  () (COMMAND "OSNAP" "MIDP"))
(DEFUN C:ON  () (COMMAND "OSNAP" "NEAR"))
(DEFUN C:OK  () (COMMAND "OSNAP" "NONE"))
(DEFUN C:OD  () (COMMAND "OSNAP" "NODE"))
(DEFUN C:OP  () (COMMAND "OSNAP" "PERP"))
(DEFUN C:OQ  () (COMMAND "OSNAP" "QUAD"))
(DEFUN C:O1  () (COMMAND "OSNAP" "END,INT,INS,NOD,CEN"))
(DEFUN C:O2  () (COMMAND "OSNAP" "MID,INS,QUA,NOD"))
(DEFUN C:O3  () (COMMAND "OSNAP" "END,INT,INS,MID,NOD,CEN"))
(DEFUN C:EIMP () (COMMAND "OSNAP" "END,INT,MID,PER"))
(DEFUN C:EMPI () (COMMAND "OSNAP" "END,INT,MID,PER"))
(DEFUN C:88  () (COMMAND "OSNAP" "END,INT,MID,PER,QUA,NOD,INS,quick"))
(DEFUN C:99  () (COMMAND "OSNAP" "END,INT,MID,PER,CEN,NOD,INS,quick"))
(DEFUN C:QC  () (COMMAND "OSNAP" "QUA,CEN"))
(DEFUN C:PC0  () (COMMAND "VPOINT" "-0.61,-0.61,0.5"))
(DEFUN C:PC1  () (COMMAND "VPOINT" "0.61,-0.61,0.5"))
(DEFUN C:PC2  () (COMMAND "VPOINT" "0.61,0.61,0.5"))
(DEFUN C:PC3  () (COMMAND "VPOINT" "-0.61,0.61,0.5"))
(DEFUN C:PC4  () (COMMAND "VPOINT" "0.61,-0.61,0.5"))
(DEFUN C:PC5  () (COMMAND "VPOINT" "0.61,-0.61,5"))
(DEFUN C:PE  () (COMMAND "PEDIT"))
(DEFUN C:PL  () (COMMAND "PLINE"))
(DEFUN C:PG  () (COMMAND "POLYGON"))
(DEFUN C:PP  () (COMMAND "PRPLOT"))
(DEFUN C:PPW  () (COMMAND "PLINEWID"))
(DEFUN C:PU  () (COMMAND "PURGE" "all"))
(DEFUN C:QT  () (COMMAND "QTEXT"))
(DEFUN C:QS  () (COMMAND "QSAVE"))
(DEFUN C:RD  () (COMMAND "RENDER"))
(DEFUN C:R   () (COMMAND "REDRAW"))
(DEFUN C:RG  () (COMMAND "REGEN"))
(DEFUN C:RT  () (COMMAND "ROTATE"))
(DEFUN C:SC  () (COMMAND "SCALE"))
(DEFUN C:SC  () (COMMAND "SCALE"))
(DEFUN C:SH  () (COMMAND "SHELL"))
(DEFUN C:S   () (COMMAND "STRETCH" "C"))
(DEFUN C:SL  () (COMMAND "SOLID"))
(DEFUN C:T   () (COMMAND "TRIM"))
(DEFUN C:TRA () (COMMAND "TRACE"))
(DEFUN C:Tal () (COMMAND "TRIM" "ALL" ""))
(DEFUN C:TN  () (COMMAND "CHANGE" PAUSE "" "" "" "STANDARD" "" "" ""))
(DEFUN C:U   () (COMMAND "UNDO"))
(DEFUN C:VI  () (COMMAND "VIEW" "W"))
(DEFUN C:VR  () (COMMAND "VIEW" "r"))
(DEFUN C:VS  () (COMMAND "VIEW" "S"))
(DEFUN C:VV2 () (COMMAND "VPORTS" "2" "V"))
(DEFUN C:VVP () (COMMAND "VPORTS"))
(DEFUN C:VV1 () (COMMAND "VPORTS" "SI"))
(DEFUN C:VV4 () (COMMAND "VPORTS" "4"))
(DEFUN C:VV3 () (COMMAND "VPORTS" "3" "L"))
(DEFUN C:VRR () (COMMAND "VIEWRES" "Y" "20000"))
(DEFUN C:Y   () (COMMAND "MULTIPLE"))
(DEFUN C:Z   () (COMMAND "ZOOM"))
(DEFUN C:ZA  () (COMMAND "ZOOM" "A"))
(DEFUN C:ZD  () (COMMAND "ZOOM" "D"))
(DEFUN C:ZE  () (COMMAND "ZOOM" "E"))
(DEFUN C:ZP  () (COMMAND "ZOOM" "P"))
(DEFUN C:ZV  () (COMMAND "ZOOM" "V"))
(DEFUN C:ZZ  () (COMMAND "ZOOM" ".5X"))
(DEFUN C:ZZZ () (COMMAND "ZOOM" ".25X"))
(DEFUN C:ZX  () (COMMAND "ZOOM" "2X"))
(DEFUN C:Z1  () (COMMAND "ZOOM" "1.2X"))
(DEFUN C:Z2  () (COMMAND "ZOOM" "2X"))
(DEFUN C:Z3  () (COMMAND "ZOOM" "3X"))
(DEFUN C:Z4  () (COMMAND "ZOOM" "4X"))
(defun c:z6  () (command "zoom" ".6x"))
(defun c:z5  () (command "zoom" ".5x"))
(DEFUN C:Z9  () (COMMAND "ZOOM" ".9X"))
(DEFUN C:Z8  () (COMMAND "ZOOM" ".8X"))
(DEFUN C:Z7  () (COMMAND "ZOOM" ".7X"))
(DEFUN C:ZXX () (COMMAND "ZOOM" "4X"))
(DEFUN C:ZI  () (COMMAND "ZOOM" "2X"))
(DEFUN C:ZO  () (COMMAND "ZOOM" ".5X"))
(DEFUN C:-   () (COMMAND "ZOOM" ".5X"))
(DEFUN C:-- () (COMMAND "ZOOM" ".25X"))
(DEFUN C:--- () (COMMAND "ZOOM" ".125X"))
(DEFUN C:+   () (COMMAND "ZOOM" "2X"))
(DEFUN C:++  () (COMMAND "ZOOM" "4X"))
(DEFUN C:+++ () (COMMAND "ZOOM" "8X"))
(DEFUN C:u3  () (COMMAND "ucs" "3"))
(DEFUN C:uP  () (COMMAND "ucs" "P"))
(DEFUN C:UU  () (COMMAND "ucs" "")  (COMMAND "PLAN" "")) 
(DEFUN C:UW  () (COMMAND "ucs" "W")) 
(DEFUN C:u1  () (COMMAND "ucs" "")  (COMMAND "ucs" "x" "90") (command "ucs" "s" "Front" ""))
(DEFUN C:u5  () (COMMAND "ucs" "")  (COMMAND "ucs" "x" "-90") (COMMAND "ucs" "z" "-180") (command "ucs" "s" "Back" ""))
(DEFUN C:u2  () (COMMAND "ucs" "")  (COMMAND "ucs" "Y" "90")  (COMMAND "ucs" "Z" "90")   (command "ucs" "s" "Right" ""))
(DEFUN C:u4  () (COMMAND "ucs" "")  (COMMAND "ucs" "Y" "-90") (COMMAND "ucs" "Z" "-90")  (command "ucs" "s" "Left" ""))
(DEFUN C:us  () (COMMAND "ucs" "s"))
(DEFUN C:us  () (COMMAND "ucs" "r"))
(DEFUN C:us1 () (COMMAND "ucs" "s" "1"))
(DEFUN C:us2 () (COMMAND "ucs" "s" "2"))
(DEFUN C:us3 () (COMMAND "ucs" "s" "3"))
(DEFUN C:us4 () (COMMAND "ucs" "s" "4"))
(DEFUN C:us5 () (COMMAND "ucs" "s" "5"))
(DEFUN C:us6 () (COMMAND "ucs" "s" "6"))
(DEFUN C:us7 () (COMMAND "ucs" "s" "7"))
(DEFUN C:us8 () (COMMAND "ucs" "s" "8"))
(DEFUN C:us9 () (COMMAND "ucs" "s" "9"))
(DEFUN C:us10 () (COMMAND "ucs" "s" "10"))
(DEFUN C:uu1 () (COMMAND "ucs" "r" "1"))
(DEFUN C:uu2 () (COMMAND "ucs" "r" "2"))
(DEFUN C:uu3 () (COMMAND "ucs" "r" "3"))
(DEFUN C:uu4 () (COMMAND "ucs" "r" "4"))
(DEFUN C:uu5 () (COMMAND "ucs" "r" "5"))
(DEFUN C:uu6 () (COMMAND "ucs" "r" "6"))
(DEFUN C:uu7 () (COMMAND "ucs" "r" "7"))
(DEFUN C:uu8 () (COMMAND "ucs" "r" "8"))
(DEFUN C:uu9 () (COMMAND "ucs" "r" "9"))
(DEFUN C:uu10 () (COMMAND "ucs" "r" "10"))
(DEFUN C:WB  () (COMMAND "WBLOCK"))
(DEFUN C:d22  () (COMMAND "DLINE" "W" "220" ))
(DEFUN C:d11  () (COMMAND "DLINE" "W" "110" ))
(DEFUN C:d2  () (COMMAND "DLINE" "W" "200" ))
(DEFUN C:d1  () (COMMAND "DLINE" "W" "100" ))
(DEFUN C:d`11 () (COMMAND "DLINE" "W" "0.1" ))
(DEFUN C:d`22 () (COMMAND "DLINE" "W" "0.2" ))
(defun c:r10   () (quaygoc 10))
(defun c:r20   () (quaygoc 20))
(defun c:r30   () (quaygoc 30))
(defun c:r40   () (quaygoc 40))
(defun c:r50   () (quaygoc 50))
(defun c:r60   () (quaygoc 60))
(defun c:r70   () (quaygoc 70))
(defun c:r80   () (quaygoc 80))
(defun c:r90   () (quaygoc 90))
(defun c:r-90  () (quaygoc -90))
(defun c:r15   () (quaygoc 15))
(defun c:r45   () (quaygoc 45))
(defun c:r75   () (quaygoc 75))
(defun c:r135  () (quaygoc 135))
(defun c:r180  () (quaygoc 180))
(defun c:r120  () (quaygoc 120))
(defun c:CH  ()  (princ "\nChon doi tuong can thay doi  !")  (setq a (ssget)) (command "change" a "" "p"))
(defun c:ccl ()  (princ "\nChon doi tuong can thay doi lop !")  (command "select" "au" pause) (setq a (ssget "p")) (command "chprop" a "" "la") (princ))
(defun c:cct ()  (princ "\nChon doi tuong can thay doi do cao (Thickness) !") (command "select" "au" pause) (setq a (ssget "p")) (command "chprop" a "" "t") (princ))
(defun c:cce (/ a)  (princ "\nChon doi tuong can thay doi cot cao do (Eleventation) !") (command "select" "au" pause) (setq a (ssget "p")) (command "change" a "" "p" "e") (princ))
(defun c:cco (/ a)  (princ "\nChon doi tuong can thay doi mau (Color) !") (command "select" "au" pause) (setq a (ssget "p")) (command "chprop" a "" "c") (princ))
(defun c:cbl (/ a)  (princ "\Chon doi tuong can thay doi mau -> BYLAYER" )  (setq a (ssget))  (command "chprop" a "" "c" "bylayer" "") (princ))
(defun c:bbB (/ a)  (princ "\Chon doi tuong can thay doi Linetype -> BYLAYER" ) (setq a (ssget))  (command "chprop" a "" "LT" "BYLAYER" ""))
(defun c:hhH (/ a)(princ "\Chon doi tuong can thay doi Linetype -> HIDDEN" )   (setq a (ssget))(command "chprop" a "" "LT" "HIDDEN" ""))
(defun c:ddD (/ a)(princ "\Chon doi tuong can thay doi Linetype -> DASHDOT" )   (setq a (ssget))(command "chprop" a "" "LT" "DASHDOT" ""))
(defun c:CCC (/ a)(princ "\Chon doi tuong can thay doi Linetype -> CONTINUOUS" )   (setq a (ssget))(command "chprop" a "" "LT" "CONTINUOUS" ""))
(defun c:cc1  () (doimau 1))
(defun c:cc2  () (doimau 2))
(defun c:cc3  () (doimau 3))
(defun c:cc4  () (doimau 4))
(defun c:cc5  () (doimau 5))
(defun c:cc6  () (doimau 6))
(defun c:cc7  () (doimau 7))
(defun c:cc8  () (doimau 8))
(defun c:cc9  () (doimau 9))
(defun c:t0       () (docao 0))
(defun c:tgh      () (docao 0.0002))
(defun c:t`1      () (docao 10))
(defun c:t`2      () (docao 20))
(defun c:t`3      () (docao 30))
(defun c:t`4      () (docao 40))
(defun c:t`5      () (docao 50))
(defun c:t`6      () (docao 60))
(defun c:t`7      () (docao 70))
(defun c:t`8      () (docao 80))
(defun c:t`9      () (docao 90))
(defun c:t`11     () (docao 110))
(defun c:t`12     () (docao 120))
(defun c:t`13     () (docao 130))
(defun c:t`14     () (docao 140))
(defun c:t`15     () (docao 150))
(defun c:t`16     () (docao 160))
(defun c:t`17     () (docao 170))
(defun c:t`18     () (docao 180))
(defun c:t`19     () (docao 190))
(defun c:t`21     () (docao 210))
(defun c:t`22     () (docao 220))
(defun c:t`23     () (docao 230))
(defun c:t`24     () (docao 240))
(defun c:t`25     () (docao 250))
(defun c:t`26     () (docao 260))
(defun c:t`27     () (docao 270))
(defun c:t`28     () (docao 280))
(defun c:t`29     () (docao 290))
(defun c:t`31     () (docao 310))
(defun c:t`32     () (docao 320))
(defun c:t`33     () (docao 330))
(defun c:t`34     () (docao 340))
(defun c:t`35     () (docao 350))
(defun c:t`36     () (docao 360))
(defun c:t`37     () (docao 370))
(defun c:t`38     () (docao 380))
(defun c:t`39     () (docao 390))
(defun c:t`41     () (docao 410))
(defun c:t`42     () (docao 420))
(defun c:t`43     () (docao 430))
(defun c:t`44     () (docao 440))
(defun c:t`45     () (docao 450))
(defun c:t`46     () (docao 460))
(defun c:t`47     () (docao 470))
(defun c:t`48     () (docao 480))
(defun c:t`49     () (docao 490))
(defun c:tt`1      () (docao -10))
(defun c:tt`2      () (docao -20))
(defun c:tt`3      () (docao -30))
(defun c:tt`4      () (docao -40))
(defun c:tt`5      () (docao -50))
(defun c:tt`6      () (docao -60))
(defun c:tt`7      () (docao -70))
(defun c:tt`8      () (docao -80))
(defun c:tt`9      () (docao -90))
(defun c:tt`11     () (docao -110))
(defun c:tt`12     () (docao -120))
(defun c:tt`13     () (docao -130))
(defun c:tt`14     () (docao -140))
(defun c:tt`15     () (docao -150))
(defun c:tt`16     () (docao -160))
(defun c:tt`17     () (docao -170))
(defun c:tt`18     () (docao -180))
(defun c:tt`19     () (docao -190))
(defun c:tt`21     () (docao -210))
(defun c:tt`22     () (docao -220))
(defun c:tt`23     () (docao -230))
(defun c:tt`24     () (docao -240))
(defun c:tt`25     () (docao -250))
(defun c:tt`26     () (docao -260))
(defun c:tt`27     () (docao -270))
(defun c:tt`28     () (docao -280))
(defun c:tt`29     () (docao -290))
(defun c:tt`31     () (docao -310))
(defun c:tt`32     () (docao -320))
(defun c:tt`33     () (docao -330))
(defun c:tt`34     () (docao -340))
(defun c:tt`35     () (docao -350))
(defun c:tt`36     () (docao -360))
(defun c:tt`37     () (docao -370))
(defun c:tt`38     () (docao -380))
(defun c:tt`39     () (docao -390))
(defun c:tt`41     () (docao -410))
(defun c:tt`42     () (docao -420))
(defun c:tt`43     () (docao -430))
(defun c:tt`44     () (docao -440))
(defun c:tt`45     () (docao -450))
(defun c:tt`46     () (docao -460))
(defun c:tt`47     () (docao -470))
(defun c:tt`48     () (docao -480))
(defun c:tt`49     () (docao -490))

(defun c:t1      () (docao 100))
(defun c:t2      () (docao 200))
(defun c:t3      () (docao 300))
(defun c:t4      () (docao 400))
(defun c:t5      () (docao 500))
(defun c:t6      () (docao 600))
(defun c:t7      () (docao 700))
(defun c:t8      () (docao 800))
(defun c:t9      () (docao 900))
(defun c:t10     () (docao 1000))
(defun c:t11     () (docao 1100))
(defun c:t12     () (docao 1200))
(defun c:t13     () (docao 1300))
(defun c:t14     () (docao 1400))
(defun c:t15     () (docao 1500))
(defun c:t16     () (docao 1600))
(defun c:t17     () (docao 1700))
(defun c:t18     () (docao 1800))
(defun c:t19     () (docao 1900))
(defun c:t20     () (docao 2000))
(defun c:t21     () (docao 2100))
(defun c:t22     () (docao 2200))
(defun c:t23     () (docao 2300))
(defun c:t24     () (docao 2400))
(defun c:t25     () (docao 2500))
(defun c:t26     () (docao 2600))
(defun c:t27     () (docao 2700))
(defun c:t28     () (docao 2800))
(defun c:t29     () (docao 2900))
(defun c:t30     () (docao 3000))
(defun c:t31     () (docao 3100))
(defun c:t32     () (docao 3200))
(defun c:t33     () (docao 3300))
(defun c:t34     () (docao 3400))
(defun c:t35     () (docao 3500))
(defun c:t36     () (docao 3600))
(defun c:t37     () (docao 3700))
(defun c:t38     () (docao 3800))
(defun c:t39     () (docao 3900))
(defun c:t40     () (docao 4000))
(defun c:t41     () (docao 4100))
(defun c:t42     () (docao 4200))
(defun c:t43     () (docao 4300))
(defun c:t44     () (docao 4400))
(defun c:t45     () (docao 4500))
(defun c:t46     () (docao 4600))
(defun c:t47     () (docao 4700))
(defun c:t48     () (docao 4800))
(defun c:t49     () (docao 4900))
(defun c:t50     () (docao 5000))
(defun c:t51     () (docao 5100))
(defun c:t52     () (docao 5200))
(defun c:t53     () (docao 5300))
(defun c:t54     () (docao 5400))
(defun c:t55     () (docao 5500))
(defun c:t56     () (docao 5600))
(defun c:t57     () (docao 5700))
(defun c:t58     () (docao 5800))
(defun c:t59     () (docao 5900))
(defun c:t60     () (docao 6000))
(defun c:t61     () (docao 6100))
(defun c:t62     () (docao 6200))
(defun c:t63     () (docao 6300))
(defun c:t64     () (docao 6400))
(defun c:t65     () (docao 6500))
(defun c:t66     () (docao 6600))
(defun c:t67     () (docao 6700))
(defun c:t68     () (docao 6800))
(defun c:t69     () (docao 6900))
(defun c:t70     () (docao 7000))
(defun c:t71     () (docao 7100))
(defun c:t72     () (docao 7200))
(defun c:t73     () (docao 7300))
(defun c:t74     () (docao 7400))
(defun c:t75     () (docao 7500))
(defun c:t76     () (docao 7600))
(defun c:t77     () (docao 7700))
(defun c:t78     () (docao 7800))
(defun c:t79     () (docao 7900))
(defun c:t80     () (docao 8000))
(defun c:t81     () (docao 8100))
(defun c:t82     () (docao 8200))
(defun c:t83     () (docao 8300))
(defun c:t84     () (docao 8400))
(defun c:t85     () (docao 8500))
(defun c:t86     () (docao 8600))
(defun c:t87     () (docao 8700))
(defun c:t88     () (docao 8800))
(defun c:t89     () (docao 8900))
(defun c:t90     () (docao 9000))
(defun c:t91     () (docao 9100))
(defun c:t92     () (docao 9200))
(defun c:t93     () (docao 9300))
(defun c:t94     () (docao 9400))
(defun c:t95     () (docao 9500))
(defun c:t96     () (docao 9600))
(defun c:t97     () (docao 9700))
(defun c:t98     () (docao 9800))
(defun c:t99     () (docao 9900))
(defun c:t100    () (docao 10000))
(defun c:t110    () (docao 11000))
(defun c:t120    () (docao 12000))
(defun c:t130    () (docao 13000))
(defun c:t140    () (docao 14000))
(defun c:t150    () (docao 15000))
(defun c:t160    () (docao 16000))
(defun c:t170    () (docao 17000))
(defun c:t180    () (docao 18000))
(defun c:t190    () (docao 19000))
(defun c:t200    () (docao 20000))
(defun c:t210    () (docao 21000))
(defun c:t220    () (docao 22000))
(defun c:t230    () (docao 23000))
(defun c:t240    () (docao 24000))
(defun c:t250    () (docao 25000))
(defun c:t260    () (docao 26000))
(defun c:t270    () (docao 27000))
(defun c:t280    () (docao 28000))
(defun c:t290    () (docao 29000))
(defun c:t300    () (docao 30000))
(defun c:t310    () (docao 31000))
(defun c:t320    () (docao 32000))
(defun c:t330    () (docao 33000))
(defun c:t340    () (docao 34000))
(defun c:t350    () (docao 35000))
(defun c:t360    () (docao 36000))
(defun c:t370    () (docao 37000))
(defun c:t380    () (docao 38000))
(defun c:t390    () (docao 39000))
(defun c:t400    () (docao 40000))
(defun c:t410    () (docao 41000))
(defun c:t420    () (docao 42000))
(defun c:t430    () (docao 43000))
(defun c:t440    () (docao 44000))
(defun c:t450    () (docao 45000))
(defun c:t460    () (docao 46000))
(defun c:t470    () (docao 47000))
(defun c:t480    () (docao 48000))
(defun c:t490    () (docao 49000))
(defun c:t500    () (docao 50000))
(defun c:t510    () (docao 51000))
(defun c:t520    () (docao 52000))
(defun c:t530    () (docao 53000))
(defun c:t540    () (docao 54000))
(defun c:t550    () (docao 55000))
(defun c:t560    () (docao 56000))
(defun c:t570    () (docao 57000))
(defun c:t580    () (docao 58000))
(defun c:t590    () (docao 59000))
(defun c:t600    () (docao 60000))
(defun c:t610    () (docao 61000))
(defun c:t620    () (docao 62000))
(defun c:t630    () (docao 63000))
(defun c:t640    () (docao 64000))
(defun c:t650    () (docao 65000))
(defun c:t660    () (docao 66000))
(defun c:t670    () (docao 67000))
(defun c:t680    () (docao 68000))
(defun c:t690    () (docao 69000))
(defun c:t700    () (docao 70000))
(defun c:t710    () (docao 71000))
(defun c:t720    () (docao 72000))
(defun c:t730    () (docao 73000))
(defun c:t740    () (docao 74000))
(defun c:t750    () (docao 75000))
(defun c:t760    () (docao 76000))
(defun c:t770    () (docao 77000))
(defun c:t780    () (docao 78000))
(defun c:t790    () (docao 79000))
(defun c:t800    () (docao 80000))
(defun c:t810    () (docao 81000))
(defun c:t820    () (docao 82000))
(defun c:t830    () (docao 83000))
(defun c:t840    () (docao 84000))
(defun c:t850    () (docao 85000))
(defun c:t860    () (docao 86000))
(defun c:t870    () (docao 87000))
(defun c:t880    () (docao 88000))
(defun c:t890    () (docao 89000))
(defun c:t900    () (docao 90000))
(defun c:t910    () (docao 91000))
(defun c:t920    () (docao 92000))
(defun c:t930    () (docao 93000))
(defun c:t940    () (docao 94000))
(defun c:t950    () (docao 95000))
(defun c:t960    () (docao 96000))
(defun c:t970    () (docao 97000))
(defun c:t980    () (docao 98000))
(defun c:t990    () (docao 99000))
(defun c:t1000   () (docao 100000))

(defun c:tt1      () (docao -100))
(defun c:tt2      () (docao -200))
(defun c:tt3      () (docao -300))
(defun c:tt4      () (docao -400))
(defun c:tt5      () (docao -500))
(defun c:tt6      () (docao -600))
(defun c:tt7      () (docao -700))
(defun c:tt8      () (docao -800))
(defun c:tt9      () (docao -900))
(defun c:tt10     () (docao -1000))
(defun c:tt11     () (docao -1100))
(defun c:tt12     () (docao -1200))
(defun c:tt13     () (docao -1300))
(defun c:tt14     () (docao -1400))
(defun c:tt15     () (docao -1500))
(defun c:tt16     () (docao -1600))
(defun c:tt17     () (docao -1700))
(defun c:tt18     () (docao -1800))
(defun c:tt19     () (docao -1900))
(defun c:tt20     () (docao -2000))
(defun c:tt21     () (docao -2100))
(defun c:tt22     () (docao -2200))
(defun c:tt23     () (docao -2300))
(defun c:tt24     () (docao -2400))
(defun c:tt25     () (docao -2500))
(defun c:tt26     () (docao -2600))
(defun c:tt27     () (docao -2700))
(defun c:tt28     () (docao -2800))
(defun c:tt29     () (docao -2900))
(defun c:tt30     () (docao -3000))
(defun c:tt31     () (docao -3100))
(defun c:tt32     () (docao -3200))
(defun c:tt33     () (docao -3300))
(defun c:tt34     () (docao -3400))
(defun c:tt35     () (docao -3500))
(defun c:tt36     () (docao -3600))
(defun c:tt37     () (docao -3700))
(defun c:tt38     () (docao -3800))
(defun c:tt39     () (docao -3900))
(defun c:tt40     () (docao -4000))
(defun c:tt41     () (docao -4100))
(defun c:tt42     () (docao -4200))
(defun c:tt43     () (docao -4300))
(defun c:tt44     () (docao -4400))
(defun c:tt45     () (docao -4500))
(defun c:tt46     () (docao -4600))
(defun c:tt47     () (docao -4700))
(defun c:tt48     () (docao -4800))
(defun c:tt49     () (docao -4900))
(defun c:tt50     () (docao -5000))
(defun c:tt51     () (docao -5100))
(defun c:tt52     () (docao -5200))
(defun c:tt53     () (docao -5300))
(defun c:tt54     () (docao -5400))
(defun c:tt55     () (docao -5500))
(defun c:tt56     () (docao -5600))
(defun c:tt57     () (docao -5700))
(defun c:tt58     () (docao -5800))
(defun c:tt59     () (docao -5900))
(defun c:tt60     () (docao -6000))
(defun c:tt61     () (docao -6100))
(defun c:tt62     () (docao -6200))
(defun c:tt63     () (docao -6300))
(defun c:tt64     () (docao -6400))
(defun c:tt65     () (docao -6500))
(defun c:tt66     () (docao -6600))
(defun c:tt67     () (docao -6700))
(defun c:tt68     () (docao -6800))
(defun c:tt69     () (docao -6900))
(defun c:tt70     () (docao -7000))
(defun c:tt71     () (docao -7100))
(defun c:tt72     () (docao -7200))
(defun c:tt73     () (docao -7300))
(defun c:tt74     () (docao -7400))
(defun c:tt75     () (docao -7500))
(defun c:tt76     () (docao -7600))
(defun c:tt77     () (docao -7700))
(defun c:tt78     () (docao -7800))
(defun c:tt79     () (docao -7900))
(defun c:tt80     () (docao -8000))
(defun c:tt81     () (docao -8100))
(defun c:tt82     () (docao -8200))
(defun c:tt83     () (docao -8300))
(defun c:tt84     () (docao -8400))
(defun c:tt85     () (docao -8500))
(defun c:tt86     () (docao -8600))
(defun c:tt87     () (docao -8700))
(defun c:tt88     () (docao -8800))
(defun c:tt89     () (docao -8900))
(defun c:tt90     () (docao -9000))
(defun c:tt91     () (docao -9100))
(defun c:tt92     () (docao -9200))
(defun c:tt93     () (docao -9300))
(defun c:tt94     () (docao -9400))
(defun c:tt95     () (docao -9500))
(defun c:tt96     () (docao -9600))
(defun c:tt97     () (docao -9700))
(defun c:tt98     () (docao -9800))
(defun c:tt99     () (docao -9900))
(defun c:tt100    () (docao -10000))
(defun c:tt110    () (docao -11000))
(defun c:tt120    () (docao -12000))
(defun c:tt130    () (docao -13000))
(defun c:tt140    () (docao -14000))
(defun c:tt150    () (docao -15000))
(defun c:tt160    () (docao -16000))
(defun c:tt170    () (docao -17000))
(defun c:tt180    () (docao -18000))
(defun c:tt190    () (docao -19000))
(defun c:tt200    () (docao -20000))
(defun c:tt210    () (docao -21000))
(defun c:tt220    () (docao -22000))
(defun c:tt230    () (docao -23000))
(defun c:tt240    () (docao -24000))
(defun c:tt250    () (docao -25000))
(defun c:tt260    () (docao -26000))
(defun c:tt270    () (docao -27000))
(defun c:tt280    () (docao -28000))
(defun c:tt290    () (docao -29000))
(defun c:tt300    () (docao -30000))
(defun c:tt310    () (docao -31000))
(defun c:tt320    () (docao -32000))
(defun c:tt330    () (docao -33000))
(defun c:tt340    () (docao -34000))
(defun c:tt350    () (docao -35000))
(defun c:tt360    () (docao -36000))
(defun c:tt370    () (docao -37000))
(defun c:tt380    () (docao -38000))
(defun c:tt390    () (docao -39000))
(defun c:tt400    () (docao -40000))
(defun c:tt410    () (docao -41000))
(defun c:tt420    () (docao -42000))
(defun c:tt430    () (docao -43000))
(defun c:tt440    () (docao -44000))
(defun c:tt450    () (docao -45000))
(defun c:tt460    () (docao -46000))
(defun c:tt470    () (docao -47000))
(defun c:tt480    () (docao -48000))
(defun c:tt490    () (docao -49000))
(defun c:tt500    () (docao -50000))
(defun c:tt510    () (docao -51000))
(defun c:tt520    () (docao -52000))
(defun c:tt530    () (docao -53000))
(defun c:tt540    () (docao -54000))
(defun c:tt550    () (docao -55000))
(defun c:tt560    () (docao -56000))
(defun c:tt570    () (docao -57000))
(defun c:tt580    () (docao -58000))
(defun c:tt590    () (docao -59000))
(defun c:tt600    () (docao -60000))
(defun c:tt610    () (docao -61000))
(defun c:tt620    () (docao -62000))
(defun c:tt630    () (docao -63000))
(defun c:tt640    () (docao -64000))
(defun c:tt650    () (docao -65000))
(defun c:tt660    () (docao -66000))
(defun c:tt670    () (docao -67000))
(defun c:tt680    () (docao -68000))
(defun c:tt690    () (docao -69000))
(defun c:tt700    () (docao -70000))
(defun c:tt710    () (docao -71000))
(defun c:tt720    () (docao -72000))
(defun c:tt730    () (docao -73000))
(defun c:tt740    () (docao -74000))
(defun c:tt750    () (docao -75000))
(defun c:tt760    () (docao -76000))
(defun c:tt770    () (docao -77000))
(defun c:tt780    () (docao -78000))
(defun c:tt790    () (docao -79000))
(defun c:tt800    () (docao -80000))
(defun c:tt810    () (docao -81000))
(defun c:tt820    () (docao -82000))
(defun c:tt830    () (docao -83000))
(defun c:tt840    () (docao -84000))
(defun c:tt850    () (docao -85000))
(defun c:tt860    () (docao -86000))
(defun c:tt870    () (docao -87000))
(defun c:tt880    () (docao -88000))
(defun c:tt890    () (docao -89000))
(defun c:tt900    () (docao -90000))
(defun c:tt910    () (docao -91000))
(defun c:tt920    () (docao -92000))
(defun c:tt930    () (docao -93000))
(defun c:tt940    () (docao -94000))
(defun c:tt950    () (docao -95000))
(defun c:tt960    () (docao -96000))
(defun c:tt970    () (docao -97000))
(defun c:tt980    () (docao -98000))
(defun c:tt990    () (docao -99000))
(defun c:tt1000   () (docao -100000))

(defun c:e0      () (caodo 0))
(defun c:e`1      () (caodo 10))
(defun c:e`2      () (caodo 20))
(defun c:e`3      () (caodo 30))
(defun c:e`4      () (caodo 40))
(defun c:e`5      () (caodo 50))
(defun c:e`6      () (caodo 60))
(defun c:e`7      () (caodo 70))
(defun c:e`8      () (caodo 80))
(defun c:e`9      () (caodo 90))
(defun c:e`11     () (caodo 110))
(defun c:e`12     () (caodo 120))
(defun c:e`13     () (caodo 130))
(defun c:e`14     () (caodo 140))
(defun c:e`15     () (caodo 150))
(defun c:e`16     () (caodo 160))
(defun c:e`17     () (caodo 170))
(defun c:e`18     () (caodo 180))
(defun c:e`19     () (caodo 190))
(defun c:e`21     () (caodo 210))
(defun c:e`22     () (caodo 220))
(defun c:e`23     () (caodo 230))
(defun c:e`24     () (caodo 240))
(defun c:e`25     () (caodo 250))
(defun c:e`26     () (caodo 260))
(defun c:e`27     () (caodo 270))
(defun c:e`28     () (caodo 280))
(defun c:e`29     () (caodo 290))
(defun c:e`31     () (caodo 310))
(defun c:e`32     () (caodo 320))
(defun c:e`33     () (caodo 330))
(defun c:e`34     () (caodo 340))
(defun c:e`35     () (caodo 350))
(defun c:e`36     () (caodo 360))
(defun c:e`37     () (caodo 370))
(defun c:e`38     () (caodo 380))
(defun c:e`39     () (caodo 390))
(defun c:e`41     () (caodo 410))
(defun c:e`42     () (caodo 420))
(defun c:e`43     () (caodo 430))
(defun c:e`44     () (caodo 440))
(defun c:e`45     () (caodo 450))
(defun c:e`46     () (caodo 460))
(defun c:e`47     () (caodo 470))
(defun c:e`48     () (caodo 480))
(defun c:e`49     () (caodo 490))

(defun c:ee`1      () (caodo -10))
(defun c:ee`2      () (caodo -20))
(defun c:ee`3      () (caodo -30))
(defun c:ee`4      () (caodo -40))
(defun c:ee`5      () (caodo -50))
(defun c:ee`6      () (caodo -60))
(defun c:ee`7      () (caodo -70))
(defun c:ee`8      () (caodo -80))
(defun c:ee`9      () (caodo -90))
(defun c:ee`11     () (caodo -110))
(defun c:ee`12     () (caodo -120))
(defun c:ee`13     () (caodo -130))
(defun c:ee`14     () (caodo -140))
(defun c:ee`15     () (caodo -150))
(defun c:ee`16     () (caodo -160))
(defun c:ee`17     () (caodo -170))
(defun c:ee`18     () (caodo -180))
(defun c:ee`19     () (caodo -190))
(defun c:ee`21     () (caodo -210))
(defun c:ee`22     () (caodo -220))
(defun c:ee`23     () (caodo -230))
(defun c:ee`24     () (caodo -240))
(defun c:ee`25     () (caodo -250))
(defun c:ee`26     () (caodo -260))
(defun c:ee`27     () (caodo -270))
(defun c:ee`28     () (caodo -280))
(defun c:ee`29     () (caodo -290))
(defun c:ee`31     () (caodo -310))
(defun c:ee`32     () (caodo -320))
(defun c:ee`33     () (caodo -330))
(defun c:ee`34     () (caodo -340))
(defun c:ee`35     () (caodo -350))
(defun c:ee`36     () (caodo -360))
(defun c:ee`37     () (caodo -370))
(defun c:ee`38     () (caodo -380))
(defun c:ee`39     () (caodo -390))
(defun c:ee`41     () (caodo -410))
(defun c:ee`42     () (caodo -420))
(defun c:ee`43     () (caodo -430))
(defun c:ee`44     () (caodo -440))
(defun c:ee`45     () (caodo -450))
(defun c:ee`46     () (caodo -460))
(defun c:ee`47     () (caodo -470))
(defun c:ee`48     () (caodo -480))
(defun c:ee`49     () (caodo -490))

(defun c:e1      () (caodo 100))
(defun c:e2      () (caodo 200))
(defun c:e3      () (caodo 300))
(defun c:e4      () (caodo 400))
(defun c:e5      () (caodo 500))
(defun c:e6      () (caodo 600))
(defun c:e7      () (caodo 700))
(defun c:e8      () (caodo 800))
(defun c:e9      () (caodo 900))
(defun c:e10     () (caodo 1000))
(defun c:e11     () (caodo 1100))
(defun c:e12     () (caodo 1200))
(defun c:e13     () (caodo 1300))
(defun c:e14     () (caodo 1400))
(defun c:e15     () (caodo 1500))
(defun c:e16     () (caodo 1600))
(defun c:e17     () (caodo 1700))
(defun c:e18     () (caodo 1800))
(defun c:e19     () (caodo 1900))
(defun c:e20     () (caodo 2000))
(defun c:e21     () (caodo 2100))
(defun c:e22     () (caodo 2200))
(defun c:e23     () (caodo 2300))
(defun c:e24     () (caodo 2400))
(defun c:e25     () (caodo 2500))
(defun c:e26     () (caodo 2600))
(defun c:e27     () (caodo 2700))
(defun c:e28     () (caodo 2800))
(defun c:e29     () (caodo 2900))
(defun c:e30     () (caodo 3000))
(defun c:e31     () (caodo 3100))
(defun c:e32     () (caodo 3200))
(defun c:e33     () (caodo 3300))
(defun c:e34     () (caodo 3400))
(defun c:e35     () (caodo 3500))
(defun c:e36     () (caodo 3600))
(defun c:e37     () (caodo 3700))
(defun c:e38     () (caodo 3800))
(defun c:e39     () (caodo 3900))
(defun c:e40     () (caodo 4000))
(defun c:e41     () (caodo 4100))
(defun c:e42     () (caodo 4200))
(defun c:e43     () (caodo 4300))
(defun c:e44     () (caodo 4400))
(defun c:e45     () (caodo 4500))
(defun c:e46     () (caodo 4600))
(defun c:e47     () (caodo 4700))
(defun c:e48     () (caodo 4800))
(defun c:e49     () (caodo 4900))
(defun c:e50     () (caodo 5000))
(defun c:e51     () (caodo 5100))
(defun c:e52     () (caodo 5200))
(defun c:e53     () (caodo 5300))
(defun c:e54     () (caodo 5400))
(defun c:e55     () (caodo 5500))
(defun c:e56     () (caodo 5600))
(defun c:e57     () (caodo 5700))
(defun c:e58     () (caodo 5800))
(defun c:e59     () (caodo 5900))
(defun c:e60     () (caodo 6000))
(defun c:e61     () (caodo 6100))
(defun c:e62     () (caodo 6200))
(defun c:e63     () (caodo 6300))
(defun c:e64     () (caodo 6400))
(defun c:e65     () (caodo 6500))
(defun c:e66     () (caodo 6600))
(defun c:e67     () (caodo 6700))
(defun c:e68     () (caodo 6800))
(defun c:e69     () (caodo 6900))
(defun c:e70     () (caodo 7000))
(defun c:e71     () (caodo 7100))
(defun c:e72     () (caodo 7200))
(defun c:e73     () (caodo 7300))
(defun c:e74     () (caodo 7400))
(defun c:e75     () (caodo 7500))
(defun c:e76     () (caodo 7600))
(defun c:e77     () (caodo 7700))
(defun c:e78     () (caodo 7800))
(defun c:e79     () (caodo 7900))
(defun c:e80     () (caodo 8000))
(defun c:e81     () (caodo 8100))
(defun c:e82     () (caodo 8200))
(defun c:e83     () (caodo 8300))
(defun c:e84     () (caodo 8400))
(defun c:e85     () (caodo 8500))
(defun c:e86     () (caodo 8600))
(defun c:e87     () (caodo 8700))
(defun c:e88     () (caodo 8800))
(defun c:e89     () (caodo 8900))
(defun c:e90     () (caodo 9000))
(defun c:e91     () (caodo 9100))
(defun c:e92     () (caodo 9200))
(defun c:e93     () (caodo 9300))
(defun c:e94     () (caodo 9400))
(defun c:e95     () (caodo 9500))
(defun c:e96     () (caodo 9600))
(defun c:e97     () (caodo 9700))
(defun c:e98     () (caodo 9800))
(defun c:e99     () (caodo 9900))
(defun c:e100    () (caodo 10000))
(defun c:e110    () (caodo 11000))
(defun c:e120    () (caodo 12000))
(defun c:e130    () (caodo 13000))
(defun c:e140    () (caodo 14000))
(defun c:e150    () (caodo 15000))
(defun c:e160    () (caodo 16000))
(defun c:e170    () (caodo 17000))
(defun c:e180    () (caodo 18000))
(defun c:e190    () (caodo 19000))
(defun c:e200    () (caodo 20000))
(defun c:e210    () (caodo 21000))
(defun c:e220    () (caodo 22000))
(defun c:e230    () (caodo 23000))
(defun c:e240    () (caodo 24000))
(defun c:e250    () (caodo 25000))
(defun c:e260    () (caodo 26000))
(defun c:e270    () (caodo 27000))
(defun c:e280    () (caodo 28000))
(defun c:e290    () (caodo 29000))
(defun c:e300    () (caodo 30000))
(defun c:e310    () (caodo 31000))
(defun c:e320    () (caodo 32000))
(defun c:e330    () (caodo 33000))
(defun c:e340    () (caodo 34000))
(defun c:e350    () (caodo 35000))
(defun c:e360    () (caodo 36000))
(defun c:e370    () (caodo 37000))
(defun c:e380    () (caodo 38000))
(defun c:e390    () (caodo 39000))
(defun c:e400    () (caodo 40000))
(defun c:e410    () (caodo 41000))
(defun c:e420    () (caodo 42000))
(defun c:e430    () (caodo 43000))
(defun c:e440    () (caodo 44000))
(defun c:e450    () (caodo 45000))
(defun c:e460    () (caodo 46000))
(defun c:e470    () (caodo 47000))
(defun c:e480    () (caodo 48000))
(defun c:e490    () (caodo 49000))
(defun c:e500    () (caodo 50000))
(defun c:e510    () (caodo 51000))
(defun c:e520    () (caodo 52000))
(defun c:e530    () (caodo 53000))
(defun c:e540    () (caodo 54000))
(defun c:e550    () (caodo 55000))
(defun c:e560    () (caodo 56000))
(defun c:e570    () (caodo 57000))
(defun c:e580    () (caodo 58000))
(defun c:e590    () (caodo 59000))
(defun c:e600    () (caodo 60000))
(defun c:e610    () (caodo 61000))
(defun c:e620    () (caodo 62000))
(defun c:e630    () (caodo 63000))
(defun c:e640    () (caodo 64000))
(defun c:e650    () (caodo 65000))
(defun c:e660    () (caodo 66000))
(defun c:e670    () (caodo 67000))
(defun c:e680    () (caodo 68000))
(defun c:e690    () (caodo 69000))
(defun c:e700    () (caodo 70000))
(defun c:e710    () (caodo 71000))
(defun c:e720    () (caodo 72000))
(defun c:e730    () (caodo 73000))
(defun c:e740    () (caodo 74000))
(defun c:e750    () (caodo 75000))
(defun c:e760    () (caodo 76000))
(defun c:e770    () (caodo 77000))
(defun c:e780    () (caodo 78000))
(defun c:e790    () (caodo 79000))
(defun c:e800    () (caodo 80000))
(defun c:e810    () (caodo 81000))
(defun c:e820    () (caodo 82000))
(defun c:e830    () (caodo 83000))
(defun c:e840    () (caodo 84000))
(defun c:e850    () (caodo 85000))
(defun c:e860    () (caodo 86000))
(defun c:e870    () (caodo 87000))
(defun c:e880    () (caodo 88000))
(defun c:e890    () (caodo 89000))
(defun c:e900    () (caodo 90000))
(defun c:e910    () (caodo 91000))
(defun c:e920    () (caodo 92000))
(defun c:e930    () (caodo 93000))
(defun c:e940    () (caodo 94000))
(defun c:e950    () (caodo 95000))
(defun c:e960    () (caodo 96000))
(defun c:e970    () (caodo 97000))
(defun c:e980    () (caodo 98000))
(defun c:e990    () (caodo 99000))
(defun c:e1000   () (caodo 100000))

(defun c:ee1      () (caodo -100))
(defun c:ee2      () (caodo -200))
(defun c:ee3      () (caodo -300))
(defun c:ee4      () (caodo -400))
(defun c:ee5      () (caodo -500))
(defun c:ee6      () (caodo -600))
(defun c:ee7      () (caodo -700))
(defun c:ee8      () (caodo -800))
(defun c:ee9      () (caodo -900))
(defun c:ee10     () (caodo -1000))
(defun c:ee11     () (caodo -1100))
(defun c:ee12     () (caodo -1200))
(defun c:ee13     () (caodo -1300))
(defun c:ee14     () (caodo -1400))
(defun c:ee15     () (caodo -1500))
(defun c:ee16     () (caodo -1600))
(defun c:ee17     () (caodo -1700))
(defun c:ee18     () (caodo -1800))
(defun c:ee19     () (caodo -1900))
(defun c:ee20     () (caodo -2000))
(defun c:ee21     () (caodo -2100))
(defun c:ee22     () (caodo -2200))
(defun c:ee23     () (caodo -2300))
(defun c:ee24     () (caodo -2400))
(defun c:ee25     () (caodo -2500))
(defun c:ee26     () (caodo -2600))
(defun c:ee27     () (caodo -2700))
(defun c:ee28     () (caodo -2800))
(defun c:ee29     () (caodo -2900))
(defun c:ee30     () (caodo -3000))
(defun c:ee31     () (caodo -3100))
(defun c:ee32     () (caodo -3200))
(defun c:ee33     () (caodo -3300))
(defun c:ee34     () (caodo -3400))
(defun c:ee35     () (caodo -3500))
(defun c:ee36     () (caodo -3600))
(defun c:ee37     () (caodo -3700))
(defun c:ee38     () (caodo -3800))
(defun c:ee39     () (caodo -3900))
(defun c:ee40     () (caodo -4000))
(defun c:ee41     () (caodo -4100))
(defun c:ee42     () (caodo -4200))
(defun c:ee43     () (caodo -4300))
(defun c:ee44     () (caodo -4400))
(defun c:ee45     () (caodo -4500))
(defun c:ee46     () (caodo -4600))
(defun c:ee47     () (caodo -4700))
(defun c:ee48     () (caodo -4800))
(defun c:ee49     () (caodo -4900))
(defun c:ee50     () (caodo -5000))
(defun c:ee51     () (caodo -5100))
(defun c:ee52     () (caodo -5200))
(defun c:ee53     () (caodo -5300))
(defun c:ee54     () (caodo -5400))
(defun c:ee55     () (caodo -5500))
(defun c:ee56     () (caodo -5600))
(defun c:ee57     () (caodo -5700))
(defun c:ee58     () (caodo -5800))
(defun c:ee59     () (caodo -5900))
(defun c:ee60     () (caodo -6000))
(defun c:ee61     () (caodo -6100))
(defun c:ee62     () (caodo -6200))
(defun c:ee63     () (caodo -6300))
(defun c:ee64     () (caodo -6400))
(defun c:ee65     () (caodo -6500))
(defun c:ee66     () (caodo -6600))
(defun c:ee67     () (caodo -6700))
(defun c:ee68     () (caodo -6800))
(defun c:ee69     () (caodo -6900))
(defun c:ee70     () (caodo -7000))
(defun c:ee71     () (caodo -7100))
(defun c:ee72     () (caodo -7200))
(defun c:ee73     () (caodo -7300))
(defun c:ee74     () (caodo -7400))
(defun c:ee75     () (caodo -7500))
(defun c:ee76     () (caodo -7600))
(defun c:ee77     () (caodo -7700))
(defun c:ee78     () (caodo -7800))
(defun c:ee79     () (caodo -7900))
(defun c:ee80     () (caodo -8000))
(defun c:ee81     () (caodo -8100))
(defun c:ee82     () (caodo -8200))
(defun c:ee83     () (caodo -8300))
(defun c:ee84     () (caodo -8400))
(defun c:ee85     () (caodo -8500))
(defun c:ee86     () (caodo -8600))
(defun c:ee87     () (caodo -8700))
(defun c:ee88     () (caodo -8800))
(defun c:ee89     () (caodo -8900))
(defun c:ee90     () (caodo -9000))
(defun c:ee91     () (caodo -9100))
(defun c:ee92     () (caodo -9200))
(defun c:ee93     () (caodo -9300))
(defun c:ee94     () (caodo -9400))
(defun c:ee95     () (caodo -9500))
(defun c:ee96     () (caodo -9600))
(defun c:ee97     () (caodo -9700))
(defun c:ee98     () (caodo -9800))
(defun c:ee99     () (caodo -9900))
(defun c:ee100    () (caodo -10000))
(defun c:ee110    () (caodo -11000))
(defun c:ee120    () (caodo -12000))
(defun c:ee130    () (caodo -13000))
(defun c:ee140    () (caodo -14000))
(defun c:ee150    () (caodo -15000))
(defun c:ee160    () (caodo -16000))
(defun c:ee170    () (caodo -17000))
(defun c:ee180    () (caodo -18000))
(defun c:ee190    () (caodo -19000))
(defun c:ee200    () (caodo -20000))
(defun c:ee210    () (caodo -21000))
(defun c:ee220    () (caodo -22000))
(defun c:ee230    () (caodo -23000))
(defun c:ee240    () (caodo -24000))
(defun c:ee250    () (caodo -25000))
(defun c:ee260    () (caodo -26000))
(defun c:ee270    () (caodo -27000))
(defun c:ee280    () (caodo -28000))
(defun c:ee290    () (caodo -29000))
(defun c:ee300    () (caodo -30000))
(defun c:ee310    () (caodo -31000))
(defun c:ee320    () (caodo -32000))
(defun c:ee330    () (caodo -33000))
(defun c:ee340    () (caodo -34000))
(defun c:ee350    () (caodo -35000))
(defun c:ee360    () (caodo -36000))
(defun c:ee370    () (caodo -37000))
(defun c:ee380    () (caodo -38000))
(defun c:ee390    () (caodo -39000))
(defun c:ee400    () (caodo -40000))
(defun c:ee410    () (caodo -41000))
(defun c:ee420    () (caodo -42000))
(defun c:ee430    () (caodo -43000))
(defun c:ee440    () (caodo -44000))
(defun c:ee450    () (caodo -45000))
(defun c:ee460    () (caodo -46000))
(defun c:ee470    () (caodo -47000))
(defun c:ee480    () (caodo -48000))
(defun c:ee490    () (caodo -49000))
(defun c:ee500    () (caodo -50000))
(defun c:ee510    () (caodo -51000))
(defun c:ee520    () (caodo -52000))
(defun c:ee530    () (caodo -53000))
(defun c:ee540    () (caodo -54000))
(defun c:ee550    () (caodo -55000))
(defun c:ee560    () (caodo -56000))
(defun c:ee570    () (caodo -57000))
(defun c:ee580    () (caodo -58000))
(defun c:ee590    () (caodo -59000))
(defun c:ee600    () (caodo -60000))
(defun c:ee610    () (caodo -61000))
(defun c:ee620    () (caodo -62000))
(defun c:ee630    () (caodo -63000))
(defun c:ee640    () (caodo -64000))
(defun c:ee650    () (caodo -65000))
(defun c:ee660    () (caodo -66000))
(defun c:ee670    () (caodo -67000))
(defun c:ee680    () (caodo -68000))
(defun c:ee690    () (caodo -69000))
(defun c:ee700    () (caodo -70000))
(defun c:ee710    () (caodo -71000))
(defun c:ee720    () (caodo -72000))
(defun c:ee730    () (caodo -73000))
(defun c:ee740    () (caodo -74000))
(defun c:ee750    () (caodo -75000))
(defun c:ee760    () (caodo -76000))
(defun c:ee770    () (caodo -77000))
(defun c:ee780    () (caodo -78000))
(defun c:ee790    () (caodo -79000))
(defun c:ee800    () (caodo -80000))
(defun c:ee810    () (caodo -81000))
(defun c:ee820    () (caodo -82000))
(defun c:ee830    () (caodo -83000))
(defun c:ee840    () (caodo -84000))
(defun c:ee850    () (caodo -85000))
(defun c:ee860    () (caodo -86000))
(defun c:ee870    () (caodo -87000))
(defun c:ee880    () (caodo -88000))
(defun c:ee890    () (caodo -89000))
(defun c:ee900    () (caodo -90000))
(defun c:ee910    () (caodo -91000))
(defun c:ee920    () (caodo -92000))
(defun c:ee930    () (caodo -93000))
(defun c:ee940    () (caodo -94000))
(defun c:ee950    () (caodo -95000))
(defun c:ee960    () (caodo -96000))
(defun c:ee970    () (caodo -97000))
(defun c:ee980    () (caodo -98000))
(defun c:ee990    () (caodo -99000))
(defun c:ee1000   () (caodo -100000))

(defun c:w`1      () (wpline 10))
(defun c:w`2      () (wpline 20))
(defun c:w`3      () (wpline 30))
(defun c:w`4      () (wpline 40))
(defun c:w`5      () (wpline 50))
(defun c:w`6      () (wpline 60))
(defun c:w`7      () (wpline 70))
(defun c:w`8      () (wpline 80))
(defun c:w`9      () (wpline 90))
(defun c:w`11     () (wpline 110))
(defun c:w`12     () (wpline 120))
(defun c:w`13     () (wpline 130))
(defun c:w`14     () (wpline 140))
(defun c:w`15     () (wpline 150))
(defun c:w`16     () (wpline 160))
(defun c:w`17     () (wpline 170))
(defun c:w`18     () (wpline 180))
(defun c:w`19     () (wpline 190))
(defun c:w`21     () (wpline 210))
(defun c:w`22     () (wpline 220))
(defun c:w`23     () (wpline 230))
(defun c:w`24     () (wpline 240))
(defun c:w`25     () (wpline 250))
(defun c:w`26     () (wpline 260))
(defun c:w`27     () (wpline 270))
(defun c:w`28     () (wpline 280))
(defun c:w`29     () (wpline 290))
(defun c:w`31     () (wpline 310))
(defun c:w`32     () (wpline 320))
(defun c:w`33     () (wpline 330))
(defun c:w`34     () (wpline 340))
(defun c:w`35     () (wpline 350))
(defun c:w`36     () (wpline 360))
(defun c:w`37     () (wpline 370))
(defun c:w`38     () (wpline 380))
(defun c:w`39     () (wpline 390))
(defun c:w`41     () (wpline 410))
(defun c:w`42     () (wpline 420))
(defun c:w`43     () (wpline 430))
(defun c:w`44     () (wpline 440))
(defun c:w`45     () (wpline 450))
(defun c:w`46     () (wpline 460))
(defun c:w`47     () (wpline 470))
(defun c:w`48     () (wpline 480))
(defun c:w`49     () (wpline 490))

(defun c:w0      () (wpline 0))
(defun c:w1      () (wpline 100))
(defun c:w2      () (wpline 200))
(defun c:w3      () (wpline 300))
(defun c:w4      () (wpline 400))
(defun c:w5      () (wpline 500))
(defun c:w6      () (wpline 600))
(defun c:w7      () (wpline 700))
(defun c:w8      () (wpline 800))
(defun c:w9      () (wpline 900))
(defun c:w10     () (wpline 1000))
(defun c:w11     () (wpline 1100))
(defun c:w12     () (wpline 1200))
(defun c:w13     () (wpline 1300))
(defun c:w14     () (wpline 1400))
(defun c:w15     () (wpline 1500))
(defun c:w16     () (wpline 1600))
(defun c:w17     () (wpline 1700))
(defun c:w18     () (wpline 1800))
(defun c:w19     () (wpline 1900))
(defun c:w20     () (wpline 2000))
(defun c:w21     () (wpline 2100))
(defun c:w22     () (wpline 2200))
(defun c:w23     () (wpline 2300))
(defun c:w24     () (wpline 2400))
(defun c:w25     () (wpline 2500))
(defun c:w26     () (wpline 2600))
(defun c:w27     () (wpline 2700))
(defun c:w28     () (wpline 2800))
(defun c:w29     () (wpline 2900))
(defun c:w30     () (wpline 3000))
(defun c:w31     () (wpline 3100))
(defun c:w32     () (wpline 3200))
(defun c:w33     () (wpline 3300))
(defun c:w34     () (wpline 3400))
(defun c:w35     () (wpline 3500))
(defun c:w36     () (wpline 3600))
(defun c:w37     () (wpline 3700))
(defun c:w38     () (wpline 3800))
(defun c:w39     () (wpline 3900))
(defun c:w40     () (wpline 4000))
(defun c:w41     () (wpline 4100))
(defun c:w42     () (wpline 4200))
(defun c:w43     () (wpline 4300))
(defun c:w44     () (wpline 4400))
(defun c:w45     () (wpline 4500))
(defun c:w46     () (wpline 4600))
(defun c:w47     () (wpline 4700))
(defun c:w48     () (wpline 4800))
(defun c:w49     () (wpline 4900))
(defun c:w50     () (wpline 5000))
(defun c:w51     () (wpline 5100))
(defun c:w52     () (wpline 5200))
(defun c:w53     () (wpline 5300))
(defun c:w54     () (wpline 5400))
(defun c:w55     () (wpline 5500))
(defun c:w56     () (wpline 5600))
(defun c:w57     () (wpline 5700))
(defun c:w58     () (wpline 5800))
(defun c:w59     () (wpline 5900))
(defun c:w60     () (wpline 6000))
(defun c:w61     () (wpline 6100))
(defun c:w62     () (wpline 6200))
(defun c:w63     () (wpline 6300))
(defun c:w64     () (wpline 6400))
(defun c:w65     () (wpline 6500))
(defun c:w66     () (wpline 6600))
(defun c:w67     () (wpline 6700))
(defun c:w68     () (wpline 6800))
(defun c:w69     () (wpline 6900))
(defun c:w70     () (wpline 7000))
(defun c:w71     () (wpline 7100))
(defun c:w72     () (wpline 7200))
(defun c:w73     () (wpline 7300))
(defun c:w74     () (wpline 7400))
(defun c:w75     () (wpline 7500))
(defun c:w76     () (wpline 7600))
(defun c:w77     () (wpline 7700))
(defun c:w78     () (wpline 7800))
(defun c:w79     () (wpline 7900))
(defun c:w81     () (wpline 8100))
(defun c:w82     () (wpline 8200))
(defun c:w83     () (wpline 8300))
(defun c:w84     () (wpline 8400))
(defun c:w85     () (wpline 8500))
(defun c:w86     () (wpline 8600))
(defun c:w87     () (wpline 8700))
(defun c:w88     () (wpline 8800))
(defun c:w89     () (wpline 8900))
(defun c:w80     () (wpline 8000))
(defun c:w90     () (wpline 9000))
(defun c:w91     () (wpline 9100))
(defun c:w92     () (wpline 9200))
(defun c:w93     () (wpline 9300))
(defun c:w94     () (wpline 9400))
(defun c:w95     () (wpline 9500))
(defun c:w96     () (wpline 9600))
(defun c:w97     () (wpline 9700))
(defun c:w98     () (wpline 9800))
(defun c:w99     () (wpline 9900))
(defun c:w100    () (wpline 10000))
(defun c:w110    () (wpline 11000))
(defun c:w120    () (wpline 12000))
(defun c:w130    () (wpline 13000))
(defun c:w140    () (wpline 14000))
(defun c:w150    () (wpline 15000))
(defun c:w160    () (wpline 16000))
(defun c:w170    () (wpline 17000))
(defun c:w180    () (wpline 18000))
(defun c:w190    () (wpline 19000))
(defun c:w200    () (wpline 20000))
(defun c:w300    () (wpline 30000))
(defun c:w400    () (wpline 40000))
(defun c:w500    () (wpline 50000))
(defun c:w600    () (wpline 60000))
(defun c:w700    () (wpline 70000))
(defun c:w800    () (wpline 80000))
(defun c:w900    () (wpline 90000))
(defun c:w1000    () (wpline 100000))

(defun c:vs0 () (command "view" "s" "0"))
(defun c:vs1 () (command "view" "s" "1"))
(defun c:vs2 () (command "view" "s" "2"))
(defun c:vs3 () (command "view" "s" "3"))
(defun c:vs4 () (command "view" "s" "4"))
(defun c:vs5 () (command "view" "s" "5"))
(defun c:vs6 () (command "view" "s" "6"))
(defun c:vs7 () (command "view" "s" "7"))
(defun c:vs8 () (command "view" "s" "8"))
(defun c:vs9 () (command "view" "s" "9"))
(defun c:vs10 () (command "view" "s" "10"))
(defun c:vs11 () (command "view" "s" "11"))
(defun c:vs12 () (command "view" "s" "12"))
(defun c:vs13 () (command "view" "s" "13"))
(defun c:vs14 () (command "view" "s" "14"))
(defun c:vs15 () (command "view" "s" "15"))
(defun c:vs16 () (command "view" "s" "16"))
(defun c:vs17 () (command "view" "s" "17"))
(defun c:vs18 () (command "view" "s" "18"))
(defun c:vs19 () (command "view" "s" "19"))
(defun c:vs20 () (command "view" "s" "20"))
(defun c:vs21 () (command "view" "s" "21"))
(defun c:vs22 () (command "view" "s" "22"))
(defun c:vs23 () (command "view" "s" "23"))
(defun c:vs24 () (command "view" "s" "24"))
(defun c:vs25 () (command "view" "s" "25"))
(defun c:vs26 () (command "view" "s" "26"))
(defun c:vs27 () (command "view" "s" "27"))
(defun c:vs28 () (command "view" "s" "28"))
(defun c:vs29 () (command "view" "s" "29"))
(defun c:vs30 () (command "view" "s" "30"))
(defun c:vs31 () (command "view" "s" "31"))
(defun c:vs32 () (command "view" "s" "32"))
(defun c:vs33 () (command "view" "s" "33"))
(defun c:vs34 () (command "view" "s" "34"))
(defun c:vs35 () (command "view" "s" "35"))
(defun c:vs36 () (command "view" "s" "36"))
(defun c:vs37 () (command "view" "s" "37"))
(defun c:vs38 () (command "view" "s" "38"))
(defun c:vs39 () (command "view" "s" "39"))
(defun c:vs40 () (command "view" "s" "40"))

(defun c:v0 () (command "view" "r" "0"))
(defun c:v1 () (command "view" "r" "1"))
(defun c:v2 () (command "view" "r" "2"))
(defun c:v3 () (command "view" "r" "3"))
(defun c:v4 () (command "view" "r" "4"))
(defun c:v5 () (command "view" "r" "5"))
(defun c:v6 () (command "view" "r" "6"))
(defun c:v7 () (command "view" "r" "7"))
(defun c:v8 () (command "view" "r" "8"))
(defun c:v9 () (command "view" "r" "9"))
(defun c:v10 () (command "view" "r" "10"))
(defun c:v11 () (command "view" "r" "11"))
(defun c:v12 () (command "view" "r" "12"))
(defun c:v13 () (command "view" "r" "13"))
(defun c:v14 () (command "view" "r" "14"))
(defun c:v15 () (command "view" "r" "15"))
(defun c:v16 () (command "view" "r" "16"))
(defun c:v17 () (command "view" "r" "17"))
(defun c:v18 () (command "view" "r" "18"))
(defun c:v19 () (command "view" "r" "19"))
(defun c:v20 () (command "view" "r" "20"))
(defun c:v21 () (command "view" "r" "21"))
(defun c:v22 () (command "view" "r" "22"))
(defun c:v23 () (command "view" "r" "23"))
(defun c:v24 () (command "view" "r" "24"))
(defun c:v25 () (command "view" "r" "25"))
(defun c:v26 () (command "view" "r" "26"))
(defun c:v27 () (command "view" "r" "27"))
(defun c:v28 () (command "view" "r" "28"))
(defun c:v29 () (command "view" "r" "29"))
(defun c:v30 () (command "view" "r" "30"))
(defun c:v31 () (command "view" "r" "31"))
(defun c:v32 () (command "view" "r" "32"))
(defun c:v33 () (command "view" "r" "33"))
(defun c:v34 () (command "view" "r" "34"))
(defun c:v35 () (command "view" "r" "35"))
(defun c:v36 () (command "view" "r" "36"))
(defun c:v37 () (command "view" "r" "37"))
(defun c:v38 () (command "view" "r" "38"))
(defun c:v39 () (command "view" "r" "39"))
(defun c:v40 () (command "view" "r" "40"))
;; ================================ MENU ====================================
(defun c:MAC () (command "MENU" "ACAD") (princ) )
(defun c:MAR () (command "MENU" "ARCHT") (princ) )
(defun c:MAD () (command "MENU" "ADCADD") (princ) )
(defun c:STA () (command "MENU" "START") (princ) )
(defun c:PLA () (command "MENU" "XDUNG") (princ) )
(defun c:TGX () (command "MENU" "TGXDKT") (princ) )
;;;========================== Thoat tam ra NC ===============================
 (DEFUN C:NC   () (COMMAND "SHELL" "C:\\NC\\NC") (PRINC))                                                                        
;;; ==================== Dieu chinh Goc Quay giao dien =======================
(DEFUN C:00 () (COMMAND "SETVAR" "SNAPANG" "0") (COMMAND "SETVAR" "ORTHOMODE" "1"))
(DEFUN C:05 () (COMMAND "SETVAR" "SNAPANG" "5") (COMMAND "SETVAR" "ORTHOMODE" "1"))
(DEFUN C:10 () (COMMAND "SETVAR" "SNAPANG" "10") (COMMAND "SETVAR" "ORTHOMODE" "1"))
(DEFUN C:82 () (COMMAND "SETVAR" "SNAPANG" "82.5") (COMMAND "SETVAR" "ORTHOMODE" "1"))
(DEFUN C:15 () (COMMAND "SETVAR" "SNAPANG" "15") (COMMAND "SETVAR" "ORTHOMODE" "1"))
(DEFUN C:30 () (COMMAND "SETVAR" "SNAPANG" "30") (COMMAND "SETVAR" "ORTHOMODE" "1"))
(DEFUN C:45 () (COMMAND "SETVAR" "SNAPANG" "45") (COMMAND "SETVAR" "ORTHOMODE" "1"))
(DEFUN C:60 () (COMMAND "SETVAR" "SNAPANG" "60") (COMMAND "SETVAR" "ORTHOMODE" "1"))
(DEFUN C:75 () (COMMAND "SETVAR" "SNAPANG" "75") (COMMAND "SETVAR" "ORTHOMODE" "1"))
;;; =========================== Layer hien hanh =============================
(defun layset (/ LAY) (setvar "cmdecho" 0)
 (setq LAY (entsel "\nPick vao doi tuong muon Layer hien hanh la Layer cua doi tuong do : "))
 (if LAY     (progn     
  (setq LAY (cdr (assoc 8 (entget (car LAY)))))
  (command "_.layer" "set" LAY "") (princ (strcat "\nLayer : " LAY " da la hien hanh."))  )
             (progn
      (if (not ddlop) (load "ddlop"))  (if (setq LAY (ddlop)) 
             (progn
            (command "_.LAYER" "ON" LAY "THAW" LAY "SET" LAY "")  (princ (strcat "\nLayer : " LAY " da la hien hanh.")) ) ) ) )(princ) )
(defun c:LL     () (layset))(defun c:LAYSET () (layset))
;;; ================== Cap nhat doi tuong vao layer hien hanh ==================
(Defun LAYCUR (/ SS CNT LAY)  (setvar "cmdecho" 0)
  (if (not (setq SS (ssget "i")))
    (progn (prompt "\nChon doi tuong cap nhat vao layer hien hanh: ")
      (setq SS (ssget))    )  )
  (if SS    (progn
   (setq CNT (sslength SS)) (princ (strcat "\n" (itoa CNT) " doi tuong tim thay."))                  (command "_.move" SS "")                      
      (if (> (getvar "cmdactive") 0)                
        (progn
          (command "0,0" "0,0") (setq SS  (ssget "p") CNT (- CNT (sslength SS))    )   )
          (setq SS nil)     )  (if (> CNT 0)                                 
          (princ (strcat "\n" (itoa CNT) " doi tuong tren layer LOCK.")) ) ) )
  (if SS    (progn
      (setq LAY (getvar "CLAYER")) (command "_.change" SS "" "_p" "_la" LAY "")
      (if (= (sslength SS) 1)
        (prompt (strcat "\n1 doi tuong da cap nhat vao layer : " LAY " (layer hien hanh)."))
        (prompt (strcat "\n" (itoa (sslength SS)) " doi tuong da cap nhat vao layer : " LAY " (layer hien hanh).")) ) ))  (princ) );end
(defun c:LAYCUR () (laycur)) (defun c:LHH    () (laycur))
;;; =========================== Layer Iso ===================================
(Defun LAYISO (/ SS CNT LAY LAYLST VAL)  (setvar "cmdecho" 0)
  (if (not (setq SS (ssget "i")))    (progn
      (prompt "\nChon doi tuong tren layer(s) muon lam viec doc lap: ")
      (setq SS (ssget))    )  )
  (if SS    (progn      (setq CNT 0)
      (while (setq LAY (ssname SS CNT))
        (setq LAY (cdr (assoc 8 (entget LAY))))
        (if (not (member LAY LAYLST))
          (setq LAYLST (cons LAY LAYLST))        )
        (setq CNT (1+ CNT))      )
      (if (member (getvar "CLAYER") LAYLST)
        (setq LAY (getvar "CLAYER"))
        (setvar "CLAYER" (setq LAY (last LAYLST)))      )
      (command "_.LAYER" "_OFF" "*" "_Y")
      (foreach VAL LAYLST (command "_ON" VAL))
      (command "")            (if (= (length LAYLST) 1)
        (prompt (strcat "\nLayer " (car LAYLST) " da tach ra."))
        (prompt (strcat "\n" (itoa (length LAYLST)) " layers da tach ra. "
                        "Layer " LAY " la hien hanh."   )  )  )  )  )  (princ) )
(defun c:LAYISO () (layiso)) (defun c:LAI () (layiso))
;;; =========================  Layer Match ==================================
(Defun LAYMCH (/ SS CNT LOOP LAY ANS)
  (setvar "cmdecho" 0)
  (if (not (setq SS (ssget "i")))    (progn
      (prompt "\nChon doi tuong muon thay doi Layer : ")
      (setq SS (ssget))    )  )
  (if SS    (progn
      (setq CNT (sslength SS))
      (princ (strcat "\n" (itoa CNT) " found."))  (command "_.move" SS "")                        
      (if (> (getvar "cmdactive") 0)   (progn
          (command "0,0" "0,0")  (setq SS  (ssget "p")
                CNT (- CNT (sslength SS))    )    )
        (setq SS nil)      )  (if (> CNT 0)                                    
          (princ (strcat "\n" (itoa CNT) " tren layer LOCK.")) ) )  )
  (if SS    (progn
      (initget "Ten")  (setq LAY  (entsel "\nTen layer/<Pick doi tuong>: ")  LOOP T  )
    (while LOOP        (cond
          ((not LAY)
            (prompt "\nKhong chon doi tuong.")
            (prompt "\nSu dung layer hien hanh? <Y> ")
            (setq ANS (strcase (getstring)))
            (if (or (= ANS "") (= ANS "Y") (= ANS "YES"))
              (setq LAY  (getvar "clayer")  LOOP nil )  )  )
          ((listp LAY)  (setq LOOP nil) )
          ((= LAY "Ten")
            (setq LAY (getstring "\n>Nhap ten layer: "))
            (cond
              ((tblsearch "LAYER" LAY)  (setq LOOP nil)   )
              ((/= LAY "")
                (prompt "\nLayer chua co trong ban ve. Tao layer moi? <Y>: ")
                (setq ANS (strcase (getstring)))
                (if (or (= ANS "") (= ANS "Y") (= ANS "YES"))
		    (progn
		        (command "_.LAYER" "NEW" LAY "")
                        (setq LOOP nil)   )
                    (prompt "\nLoi ten layer.")   )   )  )  )   )
        (if LOOP  (progn (initget "Ten")
            (setq LAY  (entsel "\nTen layer/<Pick doi tuong>: ")) ) ) ); while LOOP
        (if (listp LAY)
        (setq LAY (cdr (assoc 8 (entget (car LAY)))))      )
      (command "_.change" SS "" "_p" "_la" LAY "")
      (if SS  (prompt (strcat "\n" (itoa (sslength SS)) " doi tuong thay doi toi layer " LAY )) )
      (if (= LAY (getvar "clayer"))
        (prompt " (layer hien hanh).")  (prompt ".") ) ) )  (princ) )
(defun c:LAYMCH () (laymch)) (defun c:CLL    () (laymch))
;;; ============================ Layer OFF =================================
(DEFUN LAYOFF (/ SSET SSL ENT LAY I MODE) (setvar "cmdecho" 0) 
  (prompt "\nChon doi tuong tren layer(s) muon OFF: ")
  (SETQ SSET (SSGET))   (IF (/= NIL SSET) (PROGN
     (SETQ SSL (SSLENGTH SSET))  (SETQ LAY "") (SETQ I 0) (SETQ MODE 0) 
     (WHILE (< I SSL)
       (SETQ ENT (ENTGET (SSNAME SSET I)))
       (IF (= (CDR (ASSOC '8 ENT)) (GETVAR "CLAYER")) (SETQ MODE 1) )
       (SETQ LAY (STRCAT LAY "," (CDR (ASSOC '8 ENT)) ))  (SETQ I (+ I 1)))
     (COMMAND "LAYER" "OFF" LAY "")
     (IF (= MODE 1) (COMMAND ""))))
 (setq Loff6 Loff5) (setq Loff5 Loff4) (setq Loff4 Loff3) (setq Loff3 Loff2) (setq Loff2 Loff1) (setq Loff1 LAY)
 (princ (strcat "\n      Layer : " LAY " da OFF.")) (setvar "cmdecho" 1)   (princ))
(defun c:LAYOFF () (layoff)) (defun c:LO     () (layoff))
;;; ================================ Layer ON ==============================
(Defun LAYON ()  (setvar "cmdecho" 0)
 (setq Lay loff1) (setq Loff1 Loff2) (setq Loff2 Loff3) (setq Loff3 Loff4) (setq Loff4 Loff5) (setq Loff5 Loff6) (setq Loff6 "0")
  (Command "LAYER" "ON" Lay "") (princ (strcat "\n      Layer : " LAY " da ON."))  (princ))
(defun c:LAYON () (layon)) (defun c:LOO   () (layon))
(Defun C:OLL () (setvar "cmdecho" 0)  (Command "_.LAYER" "_ON" "*" "") (princ "\nDa ON toan bo cac Layer !") (princ))
;;; ============================== Layer Freeze ===========================
(Defun LAYFRZ (/ LAY TEMP)(setvar "cmdecho" 0) 
(prompt "\nChon doi tuong tren layer(s) muon FREEZE: ") (SETQ SSET (SSGET))
 (IF (/= NIL SSET) (PROGN
     (SETQ SSL (SSLENGTH SSET))  (SETQ LAY "") (SETQ I 0) (SETQ MODE 0) 
     (WHILE (< I SSL)
       (SETQ ENT (ENTGET (SSNAME SSET I)))
       (IF (= (CDR (ASSOC '8 ENT)) (GETVAR "CLAYER")) (SETQ MODE 1) )
       (SETQ LAY (STRCAT LAY "," (CDR (ASSOC '8 ENT)) )) (SETQ I (+ I 1)))
     (COMMAND "LAYER" "FREEZE" LAY "")
     (IF (= MODE 1) (COMMAND ""))))
 (setq Lff6 Lff5) (setq Lff5 Lff4) (setq Lff4 Lff3) (setq Lff3 Lff2) (setq Lff2 Lff1) (setq Lff1 LAY)
 (princ (strcat "\n      Layer " LAY " da FREEZE."))(setvar "cmdecho" 1) (princ) )
(defun c:LAYFRZ () (layfrz)) (defun c:LF     () (layfrz))
;;; ============================== Layer Thaw ===============================
(Defun LAYTHW ()
  (setvar "cmdecho" 0)
 (setq Lay lff1) (setq Lff1 Lff2) (setq Lff2 Lff3) (setq Lff3 Lff4) (setq Lff4 Lff5) (setq Lff5 Lff6) (setq Lff6 "0")
  (Command "_.LAYER" "_THAW" LAY "")
           (princ (strcat "\n     Layer : " LAY " da THAW."))
           (princ) )
(defun c:LAYTHW () (laythw)) (defun c:LFF    () (laythw))
(Defun C:TLL () (setvar "cmdecho" 0)  (Command "_.LAYER" "_THAW" "*" "") (princ "\nDa THAW toan bo cac Layer !")  (princ))
;;; ============================== Layer Lock ==============================
(Defun LAYLCK (/ LAY)
  (setvar "cmdecho" 0)
  (setq LAY (entsel "\n>Pick doi tuong tren layer muon LOCK: "))
  (if LAY
    (progn
      (setq LAY (cdr (assoc 8 (entget (car LAY)))))
      (Command "_.LAYER" "_LOCK" LAY "")
      (princ (strcat "\nLayer " LAY " da LOCK."))    )  )  (princ) )
(defun c:LAYLCK () (laylck)) (defun c:LK     () (laylck))
;;; ============================== Layer Lock ==============================
(Defun LAYULK (/ LAY)
  (setvar "cmdecho" 0)
  (setq LAY (entsel "\n>Pick doi tuong tren layer muon UNLOCK: "))
  (if LAY
    (progn
      (setq LAY (cdr (assoc 8 (entget (car LAY)))))
      (Command "_.LAYER" "_UNLOCK" LAY "")
      (princ (strcat "\nLayer " LAY " da UNLOCK."))    )  )  (princ) )
(defun c:LAYULK () (layulk)) (defun c:LKK    () (layulk))
;;;===================== Delete all objects of Layer ========================
(defun DELAYER (/ ocmd L S) 
  (setq ocmd (getvar "CMDECHO"))
  (setvar "CMDECHO" 0)
  (setq L (strcase (getstring "\nLayer(s) to delete: ")))
  (setq S (ssget "X" (list (cons 8 L)))) 
  (if S 
    (command "ERASE" S "")            
    (princ "Layer empty or not a valid layer name.")  ) 
  (setq S nil)                        
  (setvar "CMDECHO" ocmd)             
  (princ) ) 
(defun c:DELAYER  () (delayer)) (defun c:DELLAYER () (delayer)) (defun c:DEL      () (delayer))
;;============================= Change Color Layer ===========================
(DEFUN C:LAC (/ SSET SSL ENT COL LAY I MODE)
   (SETQ SSET (SSGET))
   (IF (/= NIL SSET) 
    (PROGN
     (SETQ SSL (SSLENGTH SSET))
     (SETQ LAY "")
     (SETQ I 0)
     (SETQ MODE 0) 
     (WHILE (< I SSL)
       	  (SETQ ENT (ENTGET (SSNAME SSET I)))
	  (IF (= (CDR (ASSOC '8 ENT)) (GETVAR "CLAYER")) (SETQ MODE 1) )
          (SETQ LAY (STRCAT LAY "," (CDR (ASSOC '8 ENT)) ))
          (SETQ I (+ I 1))     )
 (setq COL (getstring "\nNew color : "))
   (COMMAND "LAYER" "C" COL LAY "")
     (IF (= MODE 1) (COMMAND "") )    )   )
   (prompt (strcat "\nLayer has changed: " LAY))
   (setvar "cmdecho" 1) (princ) )
;;; ============================== TAO LAP LAYER ==================================
(DEFUN C:0     () (taolop 7   "0")       )
(DEFUN C:car   () (taolop 7    "CAR")    )
(DEFUN C:cay   () (taolop 3   "CAY")     )
(DEFUN C:ca1   () (taolop 1   "CAY1")    )
(DEFUN C:ca2   () (taolop 2   "CAY2")    )
(DEFUN C:ca3   () (taolop 3   "CAY3")    )
(DEFUN C:ca4   () (taolop 4   "CAY4")    )
(DEFUN C:ca5   () (taolop 5   "CAY5")    )
(DEFUN C:cu    () (taolop 1   "CUA")     )
(DEFUN C:th    () (taolop 4   "thay")    )
(DEFUN C:kt    () (taolop 9   "Dim")     )
(DEFUN C:nt    () (taolop 10  "Noithat")     )
(DEFUN C:ha    () (taolop 8   "hatch")   )
(DEFUN C:cu1   () (taolop 1   "CUA1")    )
(DEFUN C:cu2   () (taolop 2   "CUA2")    )
(DEFUN C:cu3   () (taolop 3   "CUA3")    )
(DEFUN C:cu4   () (taolop 4   "CUA4")    )
(DEFUN C:cu5   () (taolop 5   "CUA5")    )
(DEFUN C:coo   () (taolop 2   "COT")     )
(DEFUN C:co1   () (taolop 1   "COT1")    )
(DEFUN C:co2   () (taolop 2   "COT2")    )
(DEFUN C:co3   () (taolop 3   "COT3")    )
(DEFUN C:co4   () (taolop 4   "COT4")    )
(DEFUN C:co5   () (taolop 5   "COT5")    )
(DEFUN C:ThB   () (taolop 9   "ThietBi") )
(DEFUN C:Tu    () (taolop 2   "TUONG")   )
(DEFUN C:Tug   () (taolop 2   "TUONG")   )
(DEFUN C:TG1   () (taolop 1   "TUONG1")  )
(DEFUN C:TG2   () (taolop 2   "TUONG2")  )
(DEFUN C:TG3   () (taolop 3   "TUONG3")  )
(DEFUN C:TG4   () (taolop 3   "TUONG4")  )
(DEFUN C:TG5   () (taolop 5   "TUONG5")  )
(DEFUN C:Tde   () (taolop 5   "TUONGDE") )
(DEFUN C:ki    () (taolop 5 "KINH")    )
(DEFUN C:kinh  () (taolop 151 "KINH")    )
(DEFUN C:kde   () (taolop 155 "KINHDE")  )
(DEFUN C:ki1   () (taolop 141 "KINH")    )
(DEFUN C:ki2   () (taolop 151 "KINH")    )
(DEFUN C:ki3   () (taolop 141 "KINH")    )
(DEFUN C:ki4   () (taolop 151 "KINH")    )
(DEFUN C:ki5   () (taolop 141 "KINH")    )
(DEFUN C:dki   () (taolop 9   "DKINH")   )
(DEFUN C:dk1   () (taolop 1   "DKINH1")  )
(DEFUN C:dk2   () (taolop 2   "DKINH2")  )
(DEFUN C:dk3   () (taolop 3   "DKINH3")  )
(DEFUN C:dk4   () (taolop 4   "DKINH4")  )
(DEFUN C:dk5   () (taolop 5   "DKINH5")  )
(DEFUN C:tvi   () (taolop 4   "TAYVIN")  )
(DEFUN C:cti   () (taolop 9   "CONTIEN") )
(DEFUN C:lca   () (taolop 4   "LCAN")    )
(DEFUN C:lc1   () (taolop 1   "LCAN1")   )
(DEFUN C:lc2   () (taolop 2   "LCAN2")   )
(DEFUN C:lc3   () (taolop 3   "LCAN3")   )
(DEFUN C:lc4   () (taolop 4   "LCAN4")   )
(DEFUN C:lc5   () (taolop 5   "LCAN5")   )
(DEFUN C:nhp   () (taolop 9   "NhaPhu")  )
(DEFUN C:np1   () (taolop 1   "NhaPhu1") )
(DEFUN C:np2   () (taolop 2   "NhaPhu2") )
(DEFUN C:np3   () (taolop 3   "NhaPhu3") )
(DEFUN C:np4   () (taolop 4   "NhaPhu4") )
(DEFUN C:np5   () (taolop 5   "NhaPhu5") )
(DEFUN C:khg   () (taolop 9   "KHUNGBV") )
(DEFUN C:tex   () (taolop 7   "TEXT")    )
(DEFUN C:tx1   () (taolop 1   "TEXT1")   )
(DEFUN C:tx2   () (taolop 2   "TEXT2")   )
(DEFUN C:tx3   () (taolop 3   "TEXT3")   )
(DEFUN C:tx4   () (taolop 4   "TEXT4")   )
(DEFUN C:tx5   () (taolop 5   "TEXT5")   )
(DEFUN C:tru   () (taolop 1   "TRUC")    )
(DEFUN C:tham  () (taolop 3   "THAM")    )
(DEFUN C:tha   () (taolop 3   "THANG")   )
(DEFUN C:tha1  () (taolop 1   "THANG1")  )
(DEFUN C:tha2  () (taolop 2   "THANG2")  )
(DEFUN C:tha3  () (taolop 3   "THANG3")  )
(DEFUN C:tha4  () (taolop 4   "THANG4")  )
(DEFUN C:tha5  () (taolop 5   "THANG5")  )
(DEFUN C:the   () (taolop 4   "THEM")    )
(DEFUN C:mai   () (taolop 1   "MAI")     )
(DEFUN C:ma1   () (taolop 1   "MAI1")    )
(DEFUN C:ma2   () (taolop 2   "MAI2")    )
(DEFUN C:ma3   () (taolop 3   "MAI3")    )
(DEFUN C:ma4   () (taolop 4   "MAI4")    )
(DEFUN C:ma5   () (taolop 5   "MAI5")    )
(DEFUN C:sanh  () (taolop 7   "SANH")    )
(DEFUN C:sh1   () (taolop 1   "SANH1")   )
(DEFUN C:sh2   () (taolop 2   "SANH2")   )
(DEFUN C:sh3   () (taolop 3   "SANH3")   )
(DEFUN C:sh4   () (taolop 4   "SANH4")   )
(DEFUN C:sh5   () (taolop 5   "SANH5")   )
(DEFUN C:sa    () (taolop 9   "SAN")     )
(DEFUN C:sa1   () (taolop 1   "SAN1")    )
(DEFUN C:sa2   () (taolop 2   "SAN2")    )
(DEFUN C:sa3   () (taolop 3   "SAN3")    )
(DEFUN C:sa4   () (taolop 4   "SAN4")    )
(DEFUN C:sa5   () (taolop 5   "SAN5")    )
(DEFUN C:tran  () (taolop 8   "TRAN")    )
(DEFUN C:tn    () (taolop 8   "TRAN")    )
(DEFUN C:tn1   () (taolop 1   "TRAN1")   )
(DEFUN C:tn2   () (taolop 2   "TRAN2")   )
(DEFUN C:tn3   () (taolop 3   "TRAN3")   )
(DEFUN C:tn4   () (taolop 4   "TRAN4")   )
(DEFUN C:tn5   () (taolop 5   "TRAN5")   )
(DEFUN C:duong () (taolop 3   "DUONG")   )
(DEFUN C:du    () (taolop 3   "DUONG")   )
(DEFUN C:dimm  () (taolop 5   "DIM")     )
(DEFUN C:dg1   () (taolop 1   "DUONG1")  )
(DEFUN C:dg2   () (taolop 2   "DUONG2")  )
(DEFUN C:dg3   () (taolop 3   "DUONG3")  )
(DEFUN C:dg4   () (taolop 4   "DUONG4")  )
(DEFUN C:dg5   () (taolop 5   "DUONG5")  )
(DEFUN C:vhe   () (taolop 7   "VIAHE")   )
(DEFUN C:vh1   () (taolop 1   "VIAHE1")  )
(DEFUN C:vh2   () (taolop 2   "VIAHE2")  )
(DEFUN C:vh3   () (taolop 3   "VIAHE3")  )
(DEFUN C:vh4   () (taolop 4   "VIAHE4")  )
(DEFUN C:vh5   () (taolop 5   "VIAHE5")  )
(DEFUN C:Bvi   () (taolop 7   "BOVIA")   )
(DEFUN C:phao  () (taolop 3   "PHAO")    )
(DEFUN C:ph1   () (taolop 1   "PHAO1")   )
(DEFUN C:ph2   () (taolop 2   "PHAO2")   )
(DEFUN C:ph3   () (taolop 3   "PHAO3")   )
(DEFUN C:ph4   () (taolop 4   "PHAO4")   )
(DEFUN C:ph5   () (taolop 5   "PHAO5")   )
(DEFUN C:inox  () (taolop 4   "INOX")    )
(DEFUN C:sto   () (taolop 8    "STONE")  )
(DEFUN C:stone () (taolop 8    "STONE")  )
(DEFUN C:woo   () (taolop 31   "WOOD")   )
(DEFUN C:wc    () (taolop 9    "WC")     )
(DEFUN C:wood  () (taolop 31   "WOOD")   )
(DEFUN C:bhoa  () (taolop 7    "BONHOA") )
(DEFUN C:grass () (taolop 3   "GRASS")   )
(DEFUN C:ng    () (taolop 9   "NGUOI")   )
(DEFUN C:oto   () (taolop 7    "OTO")    )
(DEFUN C:hra   () (taolop 4    "HRAO")   )
(DEFUN C:ltinh () (taolop 7    "LINHTINH"))
(DEFUN C:hat   () (taolop 8    "HATCH"  ))
(DEFUN C:DDAC  () (taolop 9    "DODAC"  ))
;;;---------------- Layer TIM --------------------
(DEFUN KHUAT  () (taolop 4 "KHUAT") (command "layer" "lt" "HIDDEN" "KHUAT" ""))
(defun c:Kh () (KHUAT))
(DEFUN TIM () (taolop 9 "TIM") (command "layer" "lt" "dashdot" "tim" ""))
(defun c:tim () (tim))
(DEFUN TI  () (taolop 9 "TIM") (command "layer" "lt" "dashdot" "tim" ""))
(defun c:ti  () (tim))

;; ================ Change layer for DIM =============================
(DEFUN C:LAD (/ SSET SSL M LAY I)
   (PRINC "\nSelect dimensions :")
   (SETQ SSET (SSGET))
   (IF (/= NIL SSET) (PROGN
   (SETQ SSL (SSLENGTH SSET))
   (SETQ LAY (GETSTRING "\nNew layer : "))
   (IF (/= LAY NIL) 
      (PROGN  		
   	(SETQ I 0)
   	(WHILE (< I SSL)
       	  (SETQ M (ENTGET (SSNAME SSET I)))
          (IF (= (CDR (ASSOC '0 M)) "DIMENSION") 
              (PROGN
               (SETQ M (SUBST (CONS 8 LAY) (ASSOC 8 M) M))  (ENTMOD M) ) ) 
          (SETQ I (+ I 1))  )  ) )))  (PRINC) )
;; ================ Change layer for TEXT =============================
(DEFUN C:LAT (/ SSET SSL M LAY I)
   (PRINC "\nSelect Text :")
   (SETQ SSET (SSGET))
   (IF (/= NIL SSET) (PROGN
   (SETQ SSL (SSLENGTH SSET))
   (SETQ LAY (GETSTRING "\nNew layer : "))
   (IF (/= LAY NIL) 
      (PROGN  		
   	(SETQ I 0)
   	(WHILE (< I SSL)
       	  (SETQ M (ENTGET (SSNAME SSET I)))
          (IF (= (CDR (ASSOC '0 M)) "TEXT") 
              (PROGN
               (SETQ M (SUBST (CONS 8 LAY) (ASSOC 8 M) M))  (ENTMOD M) ) ) 
          (SETQ I (+ I 1))  )  ) )))  (PRINC) )
;;; =================== Thay doi do cao theo doi tuong khac ==================
(defun chthick ()
  (prompt "\nChon doi tuong can thay doi do cao (Thickness) : ")
  (setvar "cmdecho" 0)
          (command "select" "au" pause)
  (setq khach (ssget "p"))
  (setq chu (entsel "\nChon doi tuong co do cao can theo : "))
  (setq mp  (entget (car chu)))
  (setq th (cdr(assoc 39 mp)))
  (if (= th nil) (setq th 0.0))
          (command "CHPROP" khach "" "t" th "")
  (princ "\n Do cao hien tai cua doi tuong la : ") (princ th)
  (setvar "cmdecho" 1) (princ) )
(defun c:cth     () (chthick)) (defun c:chthick () (chthick))
;;; ======================  Match all properties ==========================
(defun MH (/ list23 lri23 mpn23 lay23 lt23 col23)
  (prompt "\nChon doi tuong can thay doi thuoc tinh: ")
  (setvar "cmdecho" 0)
  (command "select" "au" pause)
  (setq list23 (ssget "p"))
  (setq lri23 (entsel "\nChon doi tuong co thuoc tinh can theo: "))
  (command "undo" "mark")
  (setq mpn23 (entget (car lri23)))
  (setq lay23 (cdr(assoc 8 mpn23)))
  (setq lt23 (cdr(assoc 6 mpn23)))
  (setq col23 (cdr (assoc 62 mpn23)))
  (if (= lt23 nil) (setq lt23 "Bylayer"))
  (if (= lt23 "byblock") (setq lt23 "Byblock"))
  (if (= col23 nil) (setq col23 "Bylayer"))
  (if (= col23 "byblock") (setq col23 "Byblock"))
  (command "change" list23 "" "p" "la" lay23 "c" col23 "lt" lt23 "")
  (princ  "\nDoi tuong da theo .. Layer: ") (princ lay23)
  (princ " ..Color: ") (princ col23) (princ " ..Linetype: ") (princ lt23)
  (setvar "cmdecho" 1) (princ) )
(defun c:mh () (MH))
;;============================= Copy + Rotate +Scan ==========================
(defun c:CRT (/ A B C D)
  (setvar "CMDECHO" 0)
  (prompt "\nFor rotated copy")
  (ssget)
  (setq A (getpoint "\nBase point: "))
  (command "ID" A)
  (setq B (getpoint "\nNext point for Move <and ogirinal Rotate> OR <Enter> if same Base point"))
  (if (= B nil) (setq B A))
; (setq D (/ (* (getangle B "\nRotation angle <0>: ") 180.0) pi))
  (command "COPY" "P" "" A A)
  (command "REDRAW")
  (command "MOVE" "P" "" A B)
  (command "REDRAW")
(princ "\nRotate Angle:")
  (command "ROTATE" "P" "" B pause)
  (command "REDRAW")
(princ "\nOption Scale:")
  (command "SCALE" "P" "" B pause)
  (command "REDRAW")
  (setvar "CMDECHO" 1)
(princ)
)

;;; =========================== VE NET CAT CHEO =============================

(defun C:G1 (
/  ps1  ps2  pf1  pf2  pf3  pf4  pf5  pf6
   pf7  pf8  sb   sh   se   ang  old_osmode)
;   (setq old_osmode (getvar "OSMODE"))
   (setq ps1 (getpoint "\nPick first point: "))
   (setq ps2 (getpoint ps1 "\nPick second point: "))
   (setq sb 200.0 sh 400.0 se 2.0)
   (setq ang (angle ps1 ps2))
   (setq pf1 (polar ps1 ang (- 0.0 se)))
   (setq pf2 (polar ps1 ang (/ (- (distance ps1 ps2) sb) 2.0) ))
   (setq pf7 (polar pf2 ang (/ sb 3.0)))
   (setq pf3 (polar pf7 (+ ang (/ pi 2)) (/ sh 2.0)))
   (setq pf8 (polar pf7 ang (/ sb 3.0)))
   (setq pf4 (polar pf8 (- ang (/ pi 2)) (/ sh 2.0)))
   (setq pf5 (polar pf8 ang (/ sb 3.0)))
   (setq pf6 (polar ps2 ang se))
   (setvar "OSMODE" 0)
   (setvar "BLIPMODE" 0)
   (command "PLINE" pf1 pf2 pf3 pf4 pf5 pf6 "")
   (setvar "OSMODE" 177)
   (setvar "BLIPMODE" 1)
   (princ)
   )
;;=============================================================================
(defun C:G2 (
/  ps1  ps2  pf1  pf2  pf3  pf4  pf5  pf6
   pf7  pf8  sb   sh   se   ang  old_osmode)
;   (setq old_osmode (getvar "OSMODE"))
   (setq ps1 (getpoint "\nPick first point: "))
   (setq ps2 (getpoint ps1 "\nPick second point: "))
   (setq sb 300.0 sh 500.0 se 1.0)
   (setq ang (angle ps1 ps2))
   (setq pf1 (polar ps1 ang (- 0.0 se)))
   (setq pf2 (polar ps1 ang (/ (- (distance ps1 ps2) sb) 2.0) ))
   (setq pf3 (polar pf2 (+ ang (/ pi 2)) (/ sh 2.0)))
   (setq pf5 (polar pf2 ang sb))
   (setq pf4 (polar pf5 (- ang (/ pi 2)) (/ sh 2.0)))
   (setq pf6 (polar ps2 ang se))
   (setvar "OSMODE" 0)
   (setvar "BLIPMODE" 0)
   (command "PLINE" pf1 pf2 pf3 pf4 pf5 pf6 "")
   (setvar "OSMODE" 177)
   (setvar "BLIPMODE" 1)
   (princ)
   )

;;; ====================== Sua Dim Doc (Vertical) =========================
(DEFUN XX ()
 (SETQ CMD (GETVAR "CMDECHO")) (SETVAR "CMDECHO" 0) (COMMAND "UCS" "W") (SETVAR "CMDECHO" 1)
 (PROMPT"\nHay chon duong kich thuoc theo chieu Doc (Ver)") (SETQ SET (SSGET))
 (PROMPT"\nHay chon diem dat duong giong moi") (SETQ P1 (GETPOINT)) (SETQ X3 (CAR P1))
 (SETQ QUANT (SSLENGTH SET)) (SETQ INDEX 0)  (WHILE (< INDEX QUANT)
   (IF (AND(= "DIMENSION" (CDR (ASSOC 0 (SETQ A (ENTGET (SSNAME SET INDEX))))))       )
 (PROGN     (SETQ L13 (ASSOC 13 A))     (SETQ M13 (CDR L13))     (SETQ L14 (ASSOC 14 A))     (SETQ M14 (CDR L14))
   (SETQ P13 (LIST 13 X3 (CADR M13) (CADDR M13)))     (SETQ P14 (LIST 14 X3 (CADR M14) (CADDR M14)))
   (SETQ A (SUBST P13 L13 A))     (SETQ A (SUBST P14 L14 A))     (ENTMOD A) )   )
  (SETQ INDEX (+ INDEX 1)) ) (SETVAR "CMDECHO" 0) (COMMAND "UCS" "P") (SETVAR "CMDECHO" CMD)
(PRINC) ) (defun c:xx () (xx)) (defun c:sdd () (xx))
;;; ====================== Sua Dim Ngang (Horigion) =========================
(DEFUN YY ()
 (SETQ CMD (GETVAR "CMDECHO")) (SETVAR "CMDECHO" 0) (COMMAND "UCS" "W") (SETVAR "CMDECHO" 1)
 (PROMPT"\nHay chon duong kich thuoc theo chieu Ngang (Hor):") (SETQ SET (SSGET))
 (PROMPT"\nHay chon diem dat duong giong moi:") (SETQ P1 (GETPOINT)) (SETQ Y3 (CADR P1))
 (SETQ QUANT (SSLENGTH SET)) (SETQ INDEX 0)  (WHILE (< INDEX QUANT)
   (IF (AND(= "DIMENSION" (CDR (ASSOC 0 (SETQ A (ENTGET (SSNAME SET INDEX))))))       )
    (PROGN     (SETQ L13 (ASSOC 13 A))     (SETQ M13 (CDR L13))     (SETQ L14 (ASSOC 14 A))
     (SETQ M14 (CDR L14))     (SETQ P13 (LIST 13 (CAR M13) Y3 (CADDR M13)))     (SETQ T13 (CDR P13))
     (SETQ P14 (LIST 14 (CAR M14) Y3 (CADDR M14)))     (SETQ A (SUBST P13 L13 A))     (SETQ A (SUBST P14 L14 A))
     (ENTMOD A)  )  )  (SETQ INDEX (+ INDEX 1)) ) (SETVAR "CMDECHO" 0) (COMMAND "UCS" "P") (SETVAR "CMDECHO" CMD)
(PRINC) ) (defun c:yy () (yy)) (defun c:sdn () (yy))
;;; ========================== ALDIM -VERTICAL ============================
(DEFUN C:AX ()
 (SETQ CMD (GETVAR "CMDECHO")) (SETVAR "CMDECHO" 0) (COMMAND "UCS" "W") (SETVAR "CMDECHO" 1)
 (PROMPT"\nSelect dimension(s) to be aligned") (SETQ SET (SSGET))
 (PROMPT"\nSelect new dimension position") (SETQ P1 (GETPOINT)) (SETQ X3 (CAR P1))
 (SETQ QUANT (SSLENGTH SET)) (SETQ INDEX 0)  (WHILE (< INDEX QUANT)
   (IF (AND(= "DIMENSION" (CDR (ASSOC 0 (SETQ A (ENTGET (SSNAME SET INDEX))))))       )
    (PROGN     (SETQ L10 (ASSOC 10 A))     (SETQ M10 (CDR L10))     (SETQ L11 (ASSOC 11 A))
     (SETQ M11 (CDR L11))     (SETQ P10 (LIST 10 X3 (CADR M10) (CADDR M10)))
     (SETQ A (SUBST P10 L10 A))     (ENTMOD A)    )   )  (SETQ INDEX (+ INDEX 1)) ) (SETVAR "CMDECHO" 0)
 (COMMAND "UCS" "P") (SETVAR "CMDECHO" CMD) )
;;; ========================== ALDIM - HORIZON ===========================
(DEFUN C:AY ()
 (SETQ CMD (GETVAR "CMDECHO")) (SETVAR "CMDECHO" 0) (COMMAND "UCS" "W") (SETVAR "CMDECHO" 1) (PROMPT"\nSelect dimension(s) to be aligned")
 (SETQ SET (SSGET)) (PROMPT"\nSelect new dimension position") (SETQ P1 (GETPOINT))
 (SETQ Y3 (CADR P1)) (SETQ QUANT (SSLENGTH SET)) (SETQ INDEX 0)  (WHILE (< INDEX QUANT)
   (IF (AND(= "DIMENSION" (CDR (ASSOC 0 (SETQ A (ENTGET (SSNAME SET INDEX))))))       )
    (PROGN     (SETQ L10 (ASSOC 10 A))     (SETQ M10 (CDR L10))     (SETQ P10 (LIST 10 (CAR M10) Y3 (CADDR M10)))
     (SETQ A (SUBST P10 L10 A))     (ENTMOD A)   )   )  (SETQ INDEX (+ INDEX 1)) )
 (SETVAR "CMDECHO" 0) (COMMAND "UCS" "P") (SETVAR "CMDECHO" CMD) )
;;; ************************* Cac lenh MODIFY *****************************
;;; ----------------------- TRIM NHIEU DOI TUONG -------------------------
(Defun C:TR ()  (Setq CVAR (Getvar "CMDECHO"))  (Setvar "CMDECHO" 0)
  (Prompt "Select cutting edges :")  (Setq CUTEDG (Ssget))
  (Prompt "Select objects to trim :")  (Setq SS (SSget))
  (Setq LEN (SSlength SS))  (Setq I -1)
  (Setq SIDE (getpoint"pick side to trim"))  (Command "TRIM" CUTEDG "")
  (Repeat LEN
   (Setq I (1+ I))
   (Command (List(SSname SS I) SIDE))  )  (Command "")
  (Setvar "CMDECHO" CVAR)  (Princ "\nTrim complete.")  (Princ) )
;;;====================== EXTEND NHIEU DOI TUONG ===========================
(Defun C:EET ()
  (Setq CVAR (Getvar "CMDECHO"))  (Setvar "CMDECHO" 0)
  (Prompt "Chon doi tuong dich cua EXTEND :")  (Setq CUTEDG (Ssget))
  (Prompt "Chon doi tuong de Extend :")  (Setq SS (SSget))  (Setq LEN (SSlength SS))
  (Setq I -1)
  (Setq SIDE (getpoint"Chon phia de EXTEND"))  (Command "EXTEND" CUTEDG "")
  (Repeat LEN
   (Setq I (1+ I))
   (Command (List(SSname SS I) SIDE))  )  (Command "")
  (Setvar "CMDECHO" CVAR)  (Princ "Da Extend xong moi ban lam tiep")  (Princ) )
;;; ===============  EXTEND 1 DOI TUONG THEO KHOANG CACH ===============
(defun c:ETT ()  (setq os (getvar "osmode"))  (setvar "osmode" 512)
  (setq pt1 (getpoint "\nKich vao 1 dau doan thang can EXTEND  "))
  (setvar "osmode" os)
  (setq dis (getdist pt1 "\nKhoang cach can EXTEND :"))
  (command "circle" "endpoint" pt1 dis)  (command "extend" "last" "" pt1 "")  (command "erase" "last" "") (princ))
;; ================ Change width of polylines =========================
(DEFUN wp (/ a b sophantu sodem list1 ha:wid)
(PRINC "\n         Chon doi tuong can thay doi do day (Width) !") 
 (setq b (ssget)) 
 (setq sophantu (sslength b)) 
 (if (null ha:wid) (setq ha:wid (getvar "tracewid")))
 (princ "\nDo rong polyline <")
 (princ ha:wid)
 (princ ">: ")
 (initget 4)
 (setq ha:wid (getdist))
 (if (null ha:wid) (setq ha:wid (getvar "tracewid")))
 (setvar "tracewid" ha:wid)
 (setvar "cmdecho" 0)
 (setq sodem 0) 
 (repeat sophantu
  (setq a (ssname b sodem))
  (setq list1 (assoc 0 (entget a)))
    (cond
     ((= (cdr list1) "POLYLINE") (command "_Pedit" a "w" ha:wid ""))
     (PROGN (command "_Pedit" a "" "w" ha:wid ""))    ) 
 (setq sodem (1+ sodem)) )(SETVAR "cmdecho" 1)(princ))
(defun c:wp () (wp)) (defun c:pw () (wp))
;; ================ Change radius of circles ==========================
(DEFUN C:CR (/ SSET SSL M RD I)   (PRINC "\nSelect Circles :")   (SETQ SSET (SSGET))
   (IF (/= NIL SSET) (PROGN  (SETQ SSL (SSLENGTH SSET))  (INITGET 4 "")  (SETQ RD (GETDIST "\nNew radius : "))
   (IF (/= RD NIL)  (PROGN (SETQ I 0)
   (WHILE (< I SSL) (SETQ M (ENTGET (SSNAME SSET I) ) )
   (IF (= (CDR (ASSOC '0 M)) "CIRCLE") (PROGN
  (SETQ M (SUBST (CONS 40 RD) (ASSOC 40 M) M))  (ENTMOD M) ) )  (SETQ I (+ I 1)) )      )   ))) (PRINC) )
;;;============================= Hide 3DFace ===============================
(defun edge-er (n) 
  (if (/= s "Function cancelled") (princ (strcat "\nError: " n)) )  (command) (command "ucs" "p") 
  (setvar "osmode" o1)  (setvar "gridmode" g1)  (setvar "aperture" a1)
  (setvar "splframe" v1)  (setvar "ucsfollow" u1) (command "undo" "e")   (setvar "cmdecho" s1)  (setq n1 -1)
  (repeat (sslength faclst) (redraw (entupd (ssname faclst (setq n1 (1+ n1)))))  )  (setq *error* lisp-er)
  (prin1) )
(defun getval (n e)  (cdr (assoc n e)) ) (defun fltfac (ss / n1) (setq n1 0)
  (if ss (repeat (sslength ss) (if (/= (getval 0 (entget (setq e1 (ssname ss n1)))) "3DFACE") 
    (ssdel e1 ss) (setq n1 (1+ n1))      )    )  )   ss) 
(defun dsply (/ ss n1 t1)  (setvar "osmode" 0)  (initget "All Select") 
  (setq ss (if (eq (getkword "\nSelect/<All>: ") "Select")  (fltfac (ssget)) 
             (ssget "x" '((0 . "3dface")))  ) n1 -1) (setvar "osmode" 2)
  (cond (ss (princ "\n** Regenerating 3DFACE entities...") (repeat (sslength ss) 
              (ssadd (setq t1 (ssname ss (setq n1 (1+ n1)))) faclst)  (shohdn (entget (entupd t1)))) (princ "done.") T) 
    (T (princ "\nNo 3DFACE entities found.") nil)  ) ) 
(defun shohdn (e / b1 p1 p2 p3 p4) (setq b1 (getval 70 e)) (mapcar '(lambda (j k) (set j (getval k e))) 
 '(p1 p2 p3 p4)  '(10 11 12 13))   (if (= (logand b1 1) 1) (grdraw p1 p2 c1 1)  ) 
  (if (= (logand b1 2) 2) (grdraw p2 p3 c1 1)  ) (if (= (logand b1 4) 4)  (grdraw p3 p4 c1 1)  ) 
  (if (= (logand b1 8) 8) (grdraw p4 p1 c1 1)  ) ) 
(defun getfce (pt / ll ur n1 ss e1 p1)  (setq p1 (trans pt 0 2) 
        ll (trans (polar P1 (/ (* pi 5) 4) h1) 2 0) 
        ur (trans (polar P1 (/ pi 4) h1) 2 0) n1 0) (setvar "osmode" 0)
  (if (setq ss (ssget "c" ll ur)) (setq ss (fltfac ss)) ) (setvar "osmode" 2)  ss) 
(defun modfce (ss pt / n1 e1 e0 p0 b1 b2 b3) 
  (setq n1 0)
  (repeat (sslength ss) 
    (setq e1 (entget (ssname ss n1)) 
          e0 (getval -1 e1))
    (ssadd e0 faclst) 
    (mapcar '(lambda (j k) (set j (getval k e1))) 
            '(p1 p2 p3 p4) 
            '(10 11 12 13)) 
    (setq p0 (if (equal (distance p3 p4) 0 1e-8) 
               (mapcar '(lambda (j k l) (/ (+ j k l) 3)) p1 p2 p3) 
               (mapcar '(lambda (j k l m) (/ (+ j k l m) 4)) p1 p2 p3 p4) ))
    (setq b1 (getval 70 e1) 
          b2 (cond ((equal pt (inters p0 pt p1 p2) h1) 1) 
               ((equal pt (inters p0 pt p2 p3) h1) 2) 
               ((equal pt (inters p0 pt p3 p4) h1) 4) 
               ((equal pt (inters p0 pt p4 p1) h1) 8) 
               (T 0)    ) 
          b3 (+ b1 (if (= (logand b1 b2) b2)  (- b2)  b2   )   ) 
          e1 (shohdn (entmod (subst (cons 70 b3) (assoc 70 e1) e1))) 
          n1 (1+ n1))  )   T ) 
(defun c:EDGE (/ lisp-er s1 o1 g1 a1 v1 h1 u1 faclst c1 r1 t1 ss pt n e n1)
  (setq s1 (getvar "cmdecho") 
        o1 (getvar "osmode") 
        g1 (getvar "gridmode") 
        a1 (getvar "aperture") 
        v1 (getvar "splframe") 
        u1 (getvar "ucsfollow") 
        h1 (/ (getvar "viewsize") 100) 
        faclst (ssadd)  c1 7
                        r1 T)
  (setvar "cmdecho" 0)  (command "undo" "group") 
  (setvar "osmode" 2)  (setvar "gridmode" 0)  (setvar "aperture" 5)
  (setvar "splframe" 1)  (setvar "ucsfollow" 0)  (command "ucs" "W") 
  (while r1 
    (initget "Display") 
    (setq t1 (getpoint "\nDisplay/<Select edge>: ") 
          r1 (cond ((eq t1 "Display") (dsply)) 
               ((eq (type t1) 'LIST) (setq ss (getfce t1))
                (cond ((null ss) (princ " No 3DFACE edges found.")) 
                  ((= (sslength ss) 0) (princ " Entity is not a 3DFACE.")) 
                  (t (modfce ss t1))   )   ) (T nil)  )) ) 
  (command "ucs" "p") 
  (setvar "osmode" o1)  (setvar "gridmode" g1)
  (setvar "aperture" a1)  (setvar "splframe" v1)
  (setvar "ucsfollow" u1)  (command "undo" "e")   (setvar "cmdecho" s1)
  (setq n1 -1)
  (repeat (sslength faclst) 
  (redraw (entupd (ssname faclst (setq n1 (1+ n1)))))  )   (prin1) ) 
;;; ============================== TEXT Hight ===============================
(defun texthght (/ ent hght)
  (setvar "cmdecho" 1)
  (prompt (strcat"\nSelect text entity with required text height"))
  (prompt (strcat"\n."))
  (setq ent (entget (car (entsel))))
  (setq hght (cdr (assoc 40 ent)))
  (prompt (strcat"\nText height now set at "))(prin1 hght)
  (prompt (strcat"\n.")) 
    (setvar "cmdecho" 1)
    (command "DTEXT" PAUSE hght "") )
(defun c:teh () (texthght))  (defun c:texthght () (texthght))
;;; ================================ TEXT FIT ============================
(Defun c:TF ( )
  (defun setsnapang (arg /) (setvar "snapang" (angtof (angtos (cdr (assoc 50 arg)) 0 8) 0 ))  )
  (Defun LL-xyz (arg) (CAR (TextBox arg))  )
  (Defun UR-x (arg) (CAADR (TextBox arg))  )
  (Defun LL-y (arg)     (CADAR (TextBox arg))  )
  (Defun LR-xy (arg)     (List (UR-x arg) (LL-y arg))  )
   (Setq ename (CAR (EntSel "\nSelect Text to stretch/shrink:"   )  )
      Textent (If ename (EntGet ename))   )   
   (If (= (CDR (Assoc 0 textent)) "TEXT")
      (Progn (initget 0 "Start")
         (Setq  NewEnd  (Distance  (LR-xy Textent) (LL-xyz Textent) ) )
         (setsnapang Textent)                 ;set snap along text entity
         (setvar "ORTHOMODE" 1)                   ;drag along the text
         (setq 
TMP (getpoint (cdr (assoc 10 Textent)) "\nStarting Point/<Pick new ending point>: ") )
         (setvar "snapang" 0)
         (cond
           ((= (type TMP) 'STR) ;;new starting point to be selected
               (setq Start (getpoint "\nPick new starting point: "))
               (if Start  (progn
                  (command "_UCS" "_E" (cdr (assoc -1 textent)))
                  (setvar "ORTHOMODE" 1)
                  (setq NewPt
                        (if Start
          (getpoint (trans Start 0 1) " ending point: ") nil ) )
                  (if NewPt (setq NewPt (trans NewPt 1 0)))
                  (setvar "ORTHOMODE" 0)
                  (command "_UCS" "_W") ) ) )
           ((not (null TMP))    ;;new ending point selected
               (setq Start (cdr (assoc 10 Textent)) NewPt TMP)  )
           (t  (setq Start nil NewPt nil) ) )
         (if (and Start NewPt) (progn
           (setq Val (Assoc 41 Textent) ;;current width factor
                 Val (if Val (cdr Val) 1.0)  LTC_%       
          (* (/ (Distance Start NewPt) NewEnd ) Val )
                 textent (Subst (cons 41 LTC_%)
           (assoc 41 textent) textent)
  textent (subst (cons 10 Start) (assoc 10 textent) textent)
  textent (subst (cons 11 NewPt) (assoc 11 textent) textent) )
   (EntMod textent) (EntUpd (cdr (assoc -1 textent))))))) (Princ))
;;; ================ BAT -TAT CHE DO GACH CHAN TEXT =================
(defun c:tuu ()  (setvar "cmdecho" 0)
    (prompt "\nHay chon dong TEXT can gach chan ")
    (prompt "\nSelect objects: ")
    (command "select" "au" pause)
    (setq sstxt (ssget "p")
          sslen (sslength sstxt)
          ctr 0    )
    (command ".undo" "mark")
    (while (< ctr sslen)
           (setq listxt (entget (ssname sstxt ctr))
                 txttxt (cdr (assoc 1 listxt))
                 enttxt (cdr (assoc 0 listxt))   )
           (if (= enttxt "TEXT")
               (progn
                   (setq testxt (substr txttxt 1 3))
                   (if (or (= testxt "%%u") (= testxt "%%U"))
                       (setq newtxt (substr txttxt 4))
                       (setq newtxt (strcat "%%u" txttxt))    )
                   (setq listxt (subst (cons 1 newtxt) (assoc 1 listxt) listxt))
                   (entmod listxt)                ) )
            (setq ctr (1+ ctr))  )    (setvar "cmdecho" 1)    (princ))
;;; ========================== Tim & thay the TEXT ==========================
(defun frstring (str search replace / str1 str2 index find)
(setq index 0) (while  (<= index (- (strlen str) (strlen search)))  (setq index (1+ index))
(setq find (substr str index (strlen search)))  (if (= find search) (progn    (setq str1 (substr str 1 (1- index)))
(setq str2 (substr str (+ index (strlen search))))  (setq str (strcat str1 replace str2)) )  ) ) (setq str str))
(defun hai (/ dial)
 (setq dial (load_dialog "hai.dcl"))       ;;goi dialog
 (if (not (new_dialog "find" Dial)) (exit)) ;;
 (mode_tile "find" 2); Tao dau nhac tai hop thoai
 (action_tile "find" "(hai1)")
 (action_tile "replace" "(hai2)")
 (action_tile "cancel" "(done_dialog) (exit)")
 (start_dialog)      
 (unload_dialog dial))
(defun hai1 () (SETQ str1 (get_tile "find")))
(defun hai2 () (SETQ str2 (get_tile "replace")))

(defun c:TTT (/ a str str1 str2 newstr taphop sodem)
 (hai)
 (if (or (null str1) (null str2)) (princ "\nDu lieu khong hop le")
  (progn
   (setq taphop (ssget '((0 . "TEXT"))))
   (setq sodem 0)
   (if taphop
    (progn
     (Repeat (sslength taphop)
      (setq a (entget (ssname taphop sodem)))
      (setq str (cdr (assoc 1 a)))
      (setq newstr (frstring str str1 str2))
      (setq a (subst (cons 1 newstr) (assoc 1 a) a))
      (entmod a)
      (setq sodem (1+ sodem))     )    )
    (princ "\nNone "TEXT" selected")   )  ) ) (setq *error* olderr) (princ))
;;;=============================  CHTEXSTY.LSP =============================
(Defun C:CST () (Setvar "Cmdecho" 0) (Initget 1 "SE ST ")
(Setq G (Strcase (Substr (Getkword "STyle/<SElection>:")1 2)))
(Cond ((= G "SE") (Setq A (Ssget)) (Setq B (Sslength A))
(Initget 1) (Setq C (Getstring "\nEnter new text style: "))
(Extang C) (While (> B 0) (Setq B (1- B)) (Setq D (Ssname A B))
(Setq D (Entget D)) (Setq E (Assoc 7 D)) (Setq F (Cons 7 C))
(Setq D (Subst F E D)) (Setq H (Assoc 51 D)) (Setq I (Cons 51 J))
(Entmod (Subst I H D))) (Setq A nil)) ((Or (= G "ST") (= G ""))
(Initget 1) (Setq A (Strcase (Getstring
"\nEnter text style to change: "))) (Initget 1)
(Setq C (Getstring "\nEnter new text style: "))(Setq D (Entnext))
(Extang C) (While D (Princ ".") (Setq E (Entget D)) (If
(And (= "TEXT" (Cdr (Assoc 0 E))) (= A (Cdr (Assoc 7 E))))
(Progn (Setq F (Assoc 7 E)) (Setq G (Cons 7 C))
(Setq E (Subst G F E)) (Setq H (Assoc 51 E)) (Setq I (Cons 51 J))
(Entmod (Subst I H E)))) (Setq D (Entnext D))))) (Princ))

(Defun Extang (A) (Setq A (Tblsearch "STYLE" A))
(Setq J (Cdr (Assoc 50 A))))
;;; =============================== Econo line =============================
(defun C:ECO ()
       (start_timer)
       (create_layer_table)
       (if (= explode_plines? "Y")
           (explode_plines))
       (economize_by_layer)
       (if (= compress? "Y")
           (compress_by_layer))
       (restore_layers)
       (if (= compress? "Y")
           (explode_1segment_plines))
       (stop_timer))

(defun start_timer ()
       (setq deleted 0
             c_date (getvar "cdate")
             s_date (getvar "tdusrtimer")
             dwg (getvar "dwgname")
             explode_plines? (strcase (userstr (if explode_plines? explode_plines? "Y")
                                               "Explode polylines before beginning?"))
             compress? (strcase (userstr (if compress? compress? "Y")
                                         "Join touching lines into multi-segment polylines?")))
       (princ (strcat "\nStarting to process drawing " dwg " on " (parse_time c_date))))
(defun stop_timer ()
       (setq e_date (getvar "tdusrtimer")
             t_secs (* 86400.0 (- e_date s_date))
             hrs (fix (/ t_secs 3600.0))
             mns (fix (/ (- t_secs (* hrs 3600.0)) 60.0))
             secs (- t_secs (+ (* hrs 3600.0) (* mns 60.0))))
       (if (null (setq fil (open (strcat dwg ".eco") "a")))
           (progn (princ (strcat "\nCouldn't open " dwg ".eco for writing.
Writing to current directory instead."))
                  (setq fil (open (strcat dwg ".eco") "a"))))
       (princ "\nECONOMIZE active for ")
       (princ (strcat "\nStarted processing drawing " dwg " on " (parse_time c_date)) fil)
       (princ "\nECONOMIZE v. 2.1 active for " fil)
       (if (> hrs 0.0)
           (princ (strcat (itoa hrs) " hour" (if (> hrs 1) "s" "") ", ") fil))
       (if (> mns 0.0)
           (princ (strcat (itoa mns) " minute" (if (> mns 1) "s" "") ", ") fil))
       (princ (strcat (rtos secs 2 3) " seconds.") fil)
       (princ (strcat "\nFile: " dwg ": Deleted a total of " (itoa deleted) " redundant lines.") fil)
       (princ "\n--------" fil)
       (close fil)
       (if (> hrs 0.0)
           (princ (strcat (itoa hrs) " hour" (if (> hrs 1) "s" "") ", ")))
       (if (> mns 0.0)
           (princ (strcat (itoa mns) " minute" (if (> mns 1) "s" "") ", ")))
       (princ (strcat (rtos secs 2 3) " seconds."))
       (princ (strcat "\nFile: " dwg ": Deleted a total of " (itoa deleted) " redundant lines."))
       (princ))

(defun economize_by_layer ()
       (setq c_lay (getvar "clayer"))
;       (setvar "regenmode" 0)
       (setvar "cmdecho" 0)
       (setvar "blipmode" 0)
       (setvar "osmode" 0)
       (foreach lyr (mapcar 'car lyrs)
                (if (and (setq lines (ssget "x" (list (cons 0 "LINE")
                                               (cons 8 lyr)))
                               *lines* lines)
                          (setq lines_l (sslength lines)))
                    (process_lines lyr)))
        (command "layer" "t" "*" "on" "*" "s" c_lay ""))

(defun create_layer_table ()
       (setq c_lay (getvar"clayer")
             lyr_data (tblnext "layer" t)
             lyr_nm (cdr (assoc 2 lyr_data))
             lyr_thawed? (cdr (assoc 70 lyr_data))
             lyr_on? (cdr (assoc 62 lyr_data))
             lyrs (list (list lyr_nm lyr_thawed? lyr_thawed?)))
       (while (setq lyr_data (tblnext "layer"))
              (setq lyr_nm (cdr (assoc 2 lyr_data))
                    lyr_thawed? (cdr (assoc 70 lyr_data))
                    lyr_on? (cdr (assoc 62 lyr_data))
                    lyrs (cons (list lyr_nm lyr_thawed? lyr_on?) lyrs))))

(defun freeze_all_but (layr)
       (command "layer" "t" layr "on" layr "s" layr)   ;; Thaw working layer
       (foreach l (aux_remove layr (mapcar 'car lyrs)) ;; Freeze all others
                (command "f" l))
       (command ""))

; (70 . 64) thawed
; (70 . 65) frozen
; (62 . 7)  on 
; (62 . -7) off 

(defun restore_layers ()
       (command "layer")
       (setq c_lay_data (assoc c_lay lyrs)
             lyr_thawed? (cadr c_lay_data)
             lyr_on? (caddr c_lay_data))
       (if (= lyr_thawed? 65)
           (command "f" c_lay)
           (command "t" c_lay))
       (if (> lyr_on? 0)
           (command "on" c_lay)
           (command "off" c_lay))
       (command "s" c_lay)
       (foreach lr (aux_remove c_lay_data lyrs);; read layer data 
                (setq lyr_nm (car lr)          ;; from layer property table
                      lyr_thawed? (cadr lr)
                      lyr_on? (caddr lr))
                (if (= lyr_thawed? 65)
                    (command "f" lyr_nm)
                    (command "t" lyr_nm))
                (if (> lyr_on? 0)
                    (command "on" lyr_nm)
                    (command "off" lyr_nm)))
       (command ""))

(defun process_lines (layr / incr)
       (freeze_all_but layr)
       (if lines (progn (terpri)
                        (setq incr 0
                              ssl (sslength lines)
                              l_deleted 0)
                        (repeat ssl
                                (setq ln (ssname lines incr))
                                (princ (strcat "\rProcessing line "
                                               (itoa (1+ incr)) " of "
                                               (itoa lines_l)
                                               " on layer " layr))
                                (if (and ln (ssmemb ln *lines*))
                                    (compile ln))
                                (setq incr (1+ incr)))))
       (princ (strcat "\t\tDeleted " (itoa l_deleted) " redundant lines.")))

(defun compile (lin / ld *lin_ss ptlst ext_pts i sl)
       (if lin
           (progn (setq lin* lin
                        ld (get_line_data lin)
                        lin_ss (ssget "c" *p1* *p2*)
                        *lin_ss* (ss2enamlist lin_ss)
                        *lin_ss (filter_non-colinear_segments lin *lin_ss*)
                        ptlst (create_ptlst *lin_ss))
                  (if (and *lin_ss
                           (> (sslength *lin_ss) 1))
                      (progn (setq ext_pts (extreme_pts ptlst)
                                   lin1 (ssname *lin_ss 0)
                                   *lin1 (entget lin1)
                                   lyr (cdr (assoc 8 *lin1)))
                             (if (and *lin_ss 
                                      (setq *ssl (sslength *lin_ss)))   
                                 (progn (setq deleted (+ deleted *ssl)
                                              l_deleted (+ l_deleted *ssl))
                                        (command "erase" *lin_ss "")
                                        (command "layer" "m" lyr "")
                                        (command "line" (car ext_pts)
                                                        (cadr ext_pts) ""))) 
                             T)))))

(defun create_ptlst (ss / i sl l1 *l1 n1 n2 pts)
       (cond ((null ss) nil)
             ((/= (type ss) 'PICKSET) nil)
             ((< (setq sl (sslength ss)) 2) nil)
             (T (setq i 1
                      sl (sslength ss)
                      l1 (ssname ss 0)
                      *l1 (entget l1)
                      n1 (cdr (assoc 10 *l1))
                      n2 (cdr (assoc 11 *l1))
                      pts (list n1 n2))
                (repeat (1- sl)
                        (setq l1 (ssname ss i)
                              *l1 (entget l1)
                              n1 (cdr (assoc 10 *l1))
                              n2 (cdr (assoc 11 *l1)))
                        (if (null (member n1 pts))
                            (setq pts (append pts (list n1))))
                        (if (null (member n2 pts))
                            (setq pts (append pts (list n2))))
                        (setq i (1+ i)))
                pts)))

(defun filter_non-colinear_segments (lin enamlst / l sl)
       (cond ((or (null enamlst)
                  (null lin)) nil)
             (T (foreach l enamlst
                         (if (and l  ;; if line isn't parallel to test line, 
                                  (not (colinear lin l))) ;; delete it from set
                             (ssdel l lin_ss)    ;; of lines to be processed
                             (ssdel l *lines*))) ;; else, assume it will be erased.
       lin_ss)))

(defun extreme_pts (pt_list)
       (cond ((or (null pt_list)
                  (< (length pt_list) 2)) nil) ;; termination condition
             ((= (length pt_list) 2) pt_list)  ;; only 2 pts in list
             (T (setq n1 (car pt_list)         ;; find extreme points
                      n2 (cadr pt_list))
                (cond ((v-orient n1 n2)
                       (setq plst (mapcar 'xy pt_list)
                             rev_p (mapcar 'reverse plst)
                             y_coords (mapcar 'car rev_p)
                             min_y (apply 'min y_coords)
                             max_y (apply 'max y_coords)
                             _n1 (assoc min_y rev_p)
                             _n2 (assoc max_y rev_p)
                             *n1 (reverse _n1)
                             *n2 (reverse _n2)))
                      ((h-orient n1 n2)
                       (setq plst (mapcar 'xy pt_list)
                             x_coords (mapcar 'car plst)
                             min_x (apply 'min x_coords)
                             max_x (apply 'max x_coords)
                             *n1 (assoc min_x plst)
                             *n2 (assoc max_x plst)))
                      ((setq direct (diagonal n1 n2))
                       (setq plst (mapcar 'xy pt_list)
                             rev_p (mapcar 'reverse plst)
                             x_coords (mapcar 'car plst)
                             y_coords (mapcar 'car rev_p)
                             min_x (apply 'min x_coords)
                             max_x (apply 'max x_coords)
                             min_y (apply 'min y_coords)
                             max_y (apply 'max y_coords))
                       (if (= direct 'LLUR) ; if we got this far, DIRECT is non-nil
                           (setq  *n1 (list min_x min_y)
                                  *n2 (list max_x max_y))
                           (setq  *n1 (list max_x min_y)  
                                  *n2 (list min_x max_y)))))
                     (list *n1 *n2))))

(defun get_line_data (line)
       (setq elist (entget line)
             *p1* (cdr (assoc 10 elist))
             *p2* (cdr (assoc 11 elist))
             *ang1* (angle *p1* *p2*)
             h_pi* (/ pi 2.0)))

(defun colinear (lin1 lin2 / line1 line2)
       (if (and lin1 lin2
                (setq line1 (entget lin1))
                (setq line2 (entget lin2))
                (setq l1p1 (cdr (assoc 10 line1)))
                (setq l1p2 (cdr (assoc 11 line1)))
                (setq l2p1 (cdr (assoc 10 line2)))
                (setq l2p2 (cdr (assoc 11 line2)))
                (setq ang1 (rad2deg (angle l1p1 l1p2)))
                (setq ang2a (rad2deg (angle l2p1 l2p2)))
                (setq ang2b (rad2deg (angle l2p2 l2p1))))
           (progn (if (not (equal l1p1 l2p1))
                      (setq ang3 (rad2deg (angle l1p1 l2p1)))
                      (setq ang3 nil))
                  (if (not (equal l1p1 l2p2))
                      (setq ang4 (rad2deg (angle l1p1 l2p2)))
                      (setq ang3 nil))
                  (and (or (= ang1 ang2a) ; pass the test for parallelism
                           (= ang1 ang2b))
                       (or (= ang2a ang3) ; pass the test that one point
                           (= ang2b ang3) ; on the segment is colinear with
                           (= ang2a ang4) ; the test segment
                           (= ang2b ang4))))))

(defun ~= (actual_value test_value tolerance)  ;;fuzzy equality
       (if (and actual_value test_value tolerance)
           (<= (abs (- actual_value test_value)) tolerance)))

(defun DEG2RAD (ang)
       (* pi (/ ang 180.000000)))

(defun RAD2DEG (ang)
       (* ang (/ 360 (* pi 2.000000))))

(defun pos-in-list (item lst)
        (if (null (member item lst))
            nil
            (- (length lst) (length (cdr (member item lst))))))

(defun 2D-TO-3D (pt elev)   ;; Construct 3D point with elev as Z coordinate
       (if pt (append (xy pt) (list elev))
              (append (getpoint "\nFirst point: ") (list elev))))

(defun XY (pt) ;; convert 3D point to 2D
       (list (car pt) (cadr pt)))

;; find closest point in node list "nodes" to point "pt"'
(defun closest (pt nodes)
       (nth
          (1- (pos-in-list
                 (apply 'min (mapcar '(lambda (node) (distance pt node)) nodes))
                             (mapcar '(lambda (node) (distance pt node)) nodes)))
        nodes))

(defun v-orient (p1 p2) ;;are two points in a basically vertical relationship?
        (> (abs (- (cadr p1) (cadr p2))) 
           (abs (- (car p1) (car p2))))) 

(defun vertical (p1 p2)
       (= (car p1) (car p2)))

(defun horizontal (p1 p2)
       (= (cadr p1) (cadr p2)))

(defun h-orient (p1 p2) ;;are two points in a horizontal relationship?
        (< (abs (- (cadr p1) (cadr p2))) 
           (abs (- (car p1) (car p2))))) 

(defun diagonal (p1 p2 / ang1)
       (setq ang1 (rad2deg (angle p1 p2)))
       (cond ((or (= ang1 45.0)
                  (= ang1 225.0)) 'LLUR)  ;; return direction of vector
             ((or (= ang1 135.0)
                  (= ang1 315.0)) 'LRUL)  ;; return direction of vector
             (T nil)))                    ;; else, nil

(defun left-to-right (p1 p2) ;;is vector P1 P2 pointing to right?
          (and (h-orient p1 p2)
               (<= (car p1) (car p2))))

(defun right-to-left (p1 p2)  ;;is vector P1 P2 pointing to left?
          (and (h-orient p1 p2)
               (> (car p1) (car p2))))

(defun top-to-bottom (p1 p2) ;;is vector P1 P2 pointing down?
          (and (v-orient p1 p2)
               (> (cadr p1) (cadr p2))))

(defun bottom-to-top (p1 p2)  ;;is vector P1 P2 pointing up?
          (and (v-orient p1 p2)
               (<= (cadr p1) (cadr p2))))

;; convert a selection set to a list of entity lists
(defun ss2enamlist (ss / entlist ctr)
       (if ss (progn
           (setq ctr 0)
           (repeat (sslength ss)
                   (progn (setq entlist (cons (ssname ss ctr) entlist))
                          (setq ctr (1+ ctr)))))) (if entlist entlist))

;(defun ~= (actual_value test_value tolerance)  ;;fuzzy equality
;       (and (<= actual_value (+ test_value tolerance))
;            (>= actual_value (- test_value tolerance))))

(defun aux_remove (atm lst) 
       (cond ((null lst) nil) 
             ((null (member atm lst)) lst)
             ((equal atm (car lst)) (cdr lst))
             (t (append (reverse (cdr (member atm (reverse lst))))
                        (cdr (member atm lst))))))

(defun parse_time (cdate / date_str year month day hour min secs date)
       (if cdate
           (setq date_str (rtos cdate 2 6)
                 year (substr date_str 3 2)
                 month (substr date_str 5 2) 
                 day (substr date_str 7 2)
                 hour (substr date_str 10 2)
                 min (substr date_str 12 2)
                 secs (substr date_str 14 2)
                 date (strcat month "/" day "/" year "  " hour ":" min ":" secs))))

(defun explode (str / firstchr *str*)  ;; iterative text explosion
      (if (null str) nil
          (repeat (strlen str)
                  (progn
                      (setq *str* (cons (setq firstchr (substr str 1 1)) *str*))
                      (setq str (substr str 2))))) (reverse *str*))

(defun concat (lst / str)
       (if (or (null lst)
               (/= (type lst) 'LIST)) nil
           (apply 'strcat lst)))

;;;  Compresser v. 2.0

(defun explode_plines ()
       (setvar "cmdecho" 0)
       (setq plns (ssget "x" '((0 . "POLYLINE"))))
       (if plns (progn (setq lngth (sslength plns)
                             i 0)
                       (terpri)
                       (repeat lngth
                               (setq pln (ssname plns i))
                               (princ (strcat "\rExploding polyline "
                                      (itoa (1+ i))
                                      " of " (itoa lngth)))
                               (command "explode" pln)
                               (setq i (1+ i)))))
       (princ))

(defun explode_1segment_plines ()
       (setvar "cmdecho" 0)
       (setq plns (ssget "x" '((0 . "POLYLINE"))))
       (if plns (progn (setq lngth (sslength plns)
                             i 0)
                       (terpri)
                       (repeat lngth
                               (setq pln (ssname plns i))
                               (princ (strcat "\rAnalyzing polyline "
                                      (itoa (1+ i))
                                      " of " (itoa lngth)))
                               (setq num_verts (length (collect_vertices pln)))
                               (if (< num_verts 3)
                                   (progn (princ "\rExploding")
                                          (command "explode" pln)))
                               (setq i (1+ i)))))
       (princ))

(defun compress_by_layer ()
       (foreach lyr (mapcar 'car lyrs)
                (if (and (setq lines (ssget "x" (list (cons 0 "LINE")
                                               (cons 8 lyr)))
                               *lines* lines)
                          (setq lines_l (sslength lines)))
                    (compress_lines lyr))))

(defun compress_lines (layr)
       (freeze_all_but layr)
       (princ (strcat "\nCompiling lines on layer " layr "\n"))
       (while (and (setq lines (ssget "x" (list (cons 0 "LINE") (cons 8 layr))))
                   (> (setq ssl (sslength lines)) 0)
                   (setq line1 (ssname lines 0)))
               (princ "\rProcessing ")
               (princ line1)
               (command "pedit" line1 "y" "j" lines "" "x")))

(defun collect_vertices (ent / *ent* pt pts)
       (if (= (cdr (assoc 0 (setq *ent* (entget ent)))) "POLYLINE")
           (progn (setq ent (entnext ent))
                  (while (setq *ent* (entget ent) pt (cdr (assoc 10 *ent*)))
                         (setq pts (cons pt pts)
                               ent (entnext ent))))
           (princ "\ncollect_vertices: not a POLYLINE."))
       (if pts pts))

(defun userstr (dflt prmpt / var) ;;DFLT and PRMPT are strings
       (setq var (getstring (if (and dflt (/= dflt ""))
                                (strcat prmpt " <" dflt ">: ")
                                (strcat prmpt ": "))))
       (cond ((/= var "") var)
             ((and dflt (= var "")) dflt)
             (T (*error* "no default given"))))

;;;================================   ACAD   =====================================
;;; ====================== Tutorial Utility Functions ==========================
(defun playtbk (book / exe full fbook)
  (setq exe   (findfile "tbook.exe"))  (setq full (strcat book ".tbk"))
  (if exe(setq fbook 
   (cond
        ((findfile full)) ((findfile book)) (T nil)       )    )  )
  (if (and exe fbook) (startapp exe fbook) (alert "Cannot run tutorial.")  ))
;;;=== AME and Region Modeler Functions ===
(defun ai_setup (len area lu mass vol)
  (setq m:err *error* *error* *merrmsg*)
  (ai_loadame)
  (if (not (not SOLUNION))
    (progn
      (sollength len)
      (solareau area)
      (setvar "lunits" lu)
      (princ "\nLength unit is set to ")(princ len)(princ ". ")
      (princ "Area unit is set to ")(princ area)(princ ".\n")
       (if (not (not SOLBOX))
         (progn
            (solmass mass)    ;don't ask for regions
            (solvolume vol)   ;don't ask for regions
            (princ "Mass unit is set to ")(princ mass)(princ ". ")
            (princ "Volume unit is set to ")(princ vol)(princ ".\n")         ) )
      (c:soldisplay) (c:solwdens)    )  )
  (setq *error* m:err m:err nil)  (princ))
(defun ai_upgvar ()
  (setq m:err *error* *error* *merrmsg*)
  (ai_loadame)
  (if (not (not SOLUNION))
    (progn
     (solhangle 45)
     (solhpat "U")
     (solsolidify 3)
     (princ "\nVariables Upgraded. Objects will be automatically solidified.")
    )  )  (setq *error* m:err m:err nil)  (princ))
(defun ai_upgprec ()
  (setq m:err *error* *error* *merrmsg*)
  (ai_loadame)
  (if (not (not SOLUNION))
    (progn
      (solupgrade 1)
      (solpurge "bfile")
      (princ "\nAME R1 solids will be converted to Double Precision.")    )  )
  (setq *error* m:err m:err nil)  (princ))
(defun ai_scrcomp ()
  (setq m:err *error* *error* *merrmsg*)
  (ai_loadame)
  (if (not (not SOLUNION))
    (progn
      (solamecomp "ame1")
      (princ "\nScript compatibility set to AME R1.")    )  )
  (setq *error* m:err m:err nil)  (princ))
(defun ai_loadame ()
  (setq m:err *error* *error* *merrmsg*)
  (if (not SOLUNION)
    (if (or (findfile "region.exp") (findfile "region"))
      (_autoxload "region")
      (_autoxload "ame")    )  )
  (setq *error* m:err m:err nil)  (princ))
(defun ai_unloadame ()
  (setq m:err *error* *error* *merrmsg*)
  (if (xunload "ame" nil)
    (progn
      (ai_aloadame)
      (princ "\nAME unloaded.\n")    )  )
  (if (xunload "region" nil)
    (progn
      (autoxload "region" '("solidify" "solint" "solsub" "solunion" "solarea"
                            "solmove" "solchp" "solsep" "sollist" "solmassp"
                            "sollength" "solvar" "solmesh" "solwire" "solfeat"
                            "solwdens" "solucs" "solpurge" "ddsolvar"
                            "ddsolmassp" "solamever" "solareau" "solaxcol"
                            "soldelent" "soldisplay" "solhangle" "solhpat"
                            "solhsize" "sollength" "solpagelen" "solrender"
                            "solservmsg" "solsolidify" "solmatcurr")      )
      (if (or (findfile "ame.exp") (findfile "ame"))
        (ai_amegrey " ")      )
      (princ "\nRegion unloaded.\n")    )  )
  (menucmd "S=X")  (menucmd "S=S")  (setq *error* m:err m:err nil)  (princ))
(defun ai_select (/ load)
  (setq m:err *error* *error* *merrmsg*)
  (if (and
        (or (findfile "ame.exp") (findfile "ame"))
        (or (findfile "region.exp") (findfile "region"))      )
    (progn
      (princ "\nNo modeler is loaded yet. ")
      (princ "Both AME and Region Modeler are available. ")
      (initget "Ame Region" )
      (setq load (getkword "\nAutoload Region/<AME>: "))
      (if (= load "Region")
        (setq app "region")
        (setq app "ame")      )    )  )
  (setq *error* m:err m:err nil)  (princ))
(defun ai_amegrey (action)
  (foreach a '(1 2 4 13 15 16 27 28 33 35 36 44 45 47 50 51)
    (menucmd (strcat "P9." (itoa a) "=" action))  ))
(defun ai_aloadame (/ exist_reg)
 (if (null c:solunion)
  (progn
  (setq m:err *error* *error* *merrmsg*)
  (if (or (findfile "region.exp") (findfile "region"))
    (progn
      (setq exist_reg "yes")
      (autoxload "region" '("solidify" "solint" "solsub" "solunion" "solarea"
                            "solmove" "solchp" "solsep" "sollist" "solmassp"
                            "sollength" "solvar" "solmesh" "solwire" "solfeat"
                            "solwdens" "solucs" "solpurge" "ddsolvar"
                            "ddsolmassp" "solamever" "solareau" "solaxcol"
                            "soldelent" "soldisplay" "solhangle" "solhpat"
                            "solhsize" "sollength" "solpagelen" "solrender"
                            "solservmsg" "solsolidify" "solmatcurr")      )
      (autoxload "ame" '("solbox" "solcone" "solcyl" "solsphere" "soltorus"
                         "solwedge" "solext" "solrev" "solcham" "solfill"
                         "solcut" "solinterf" "soldecomp" "solsubdiv"
                         "solmass" "solvolume" "solsect" "solprof"
                         "solmat" "solin" "solout" "ddsolmat" "solamecomp"
               "solmass" "solsectype" "solupgrade" "solvolume")      )    )
    (autoxload "ame" '("solbox" "solcone" "solcyl" "solsphere" "soltorus"
                       "solwedge" "solext" "solrev" "solidify" "solint"
                       "solsub" "solunion" "solcham" "solfill" "solcut"
                       "solmove" "solchp" "solsep" "sollist" "solmassp"
                       "solarea" "solinterf" "soldecomp" "solsubdiv"
                       "sollength" "solmass" "solvar" "solvolume" "solmesh"
                       "solwire" "solfeat" "solsect" "solprof" "solwdens"
                       "solmat" "solucs" "solin" "solout" "solpurge"
                       "ddsolvar" "ddsolmassp" "ddsolmat" "solamecomp"
                       "solamever" "solareau" "solaxcol" "soldelent"
                       "soldisplay" "solhangle" "solhpat" "solhsize"
                       "sollength" "solmass" "solmatcurr" "solpagelen"
                       "solrender" "solsectype" "solservmsg" "solsolidify"
                       "solupgrade" "solvolume" )  )  )
  (if (and
        (null (or (findfile "ame.exp") (findfile "ame")))
        (= exist_reg "yes") ) (ai_amegrey "~")
  )  (setq *error* m:err m:err nil)  ) ) (princ))
;;;============================= AVE Render Functions ============================
(defun ai_loadaverendr ()
  (if (null c:render)
    (autoxload "averendr" '("render" "light" "scene" "finish" "rpref"
                            "stats" "replay" "saveimg" "rconfig"))) (princ))
(defun c:ai_unloadave ()
  (princ "\n")
  (if (xunload "averendr" nil)
    (progn
      (princ "\nRender unloaded.\n")
      (ai_loadaverendr)    )  )
  (menucmd "S=X")
  (menucmd "S=S")  (princ))
;;;============================== ASE Functions =============================
(defun ai_asegrey (action)
  (foreach a '(11 13 14 16 17 19 20 21 23 24 26 27 28 29 30 31 32 33
               34 35 36 37 38 39 40 41 42 43 44 45 46 47 48 50 51)
    (menucmd (strcat "P1." (itoa a) "=" action))  )
  (if (= action "~")
    (progn
      (setq ai_aseinit_yet nil)
      (menucmd "P1.10= ")    )    (menucmd "P1.10=~")  ))
(defun ai_aseinit_chk ()
  (menucmd "S=X")
  (if ai_aseinit_yet
    (menucmd "S=ASE")
    (menucmd "S=ASEINIT0")
  )  (princ))
(defun ai_aseinit ()
  (setq m:err *error* *error* *merrmsg*)
  (if (= nil c:aseinit)
    (progn
      (princ "\nAutoCAD SQL Extension")
      (if (and (or (/= nil (findfile "ase"))
                   (/= nil (findfile "ase.exp"))
                   (/= nil (findfile "ase.exe"))
               )   (/= nil (findfile "ase.lsp"))          )
        (progn
          (xload "ase")
          (load "ase.lsp")
          (ai_asegrey " ")
          (menucmd "S=X")
          (menucmd "S=ASE")
          (setq ai_aseinit_yet T)
          (princ " loaded.")
          (c:aseinit)        )
        (progn
          (princ " not loaded.")
          (princ "\nThe ASE files were not found in your search path directories.")
          (princ "\nCheck the installation of the SQL Extension and try again.")
        )      )    )
    (progn
      (ai_asegrey " ")
      (menucmd "S=X")
      (menucmd "S=ASE")
      (if (not ai_aseinit_yet)
        (progn
          (if (findfile "ase.lsp")
            (load "ase.lsp")
            (princ "\nASE.LSP not found.  'Quick' commands not available.")
          )          (c:aseinit)        )      )
      (setq ai_aseinit_yet T)    )  )
  (setq *error* m:err m:err nil)
  (princ))
(defun ai_aseterm ()
  (setq m:err *error* *error* *merrmsg*)
  (if (= ase_errno 0)
    (progn
      (xunload "ase")
      (ai_asegrey "~")
      (menucmd "S=X")
      (menucmd "S=S")
      (princ "\nAutoCAD SQL Extension unloaded.")    )  )
  (setq *error* m:err m:err nil)  (princ))
;;; ================================ AutoLoad ================================
(defun _autoqload (quoi app cmdliste / qapp symnam)
  (setq qapp (strcat "\"" app "\""))
  (mapcar
   '(lambda (cmd / nom_cmd)
      (progn
        (setq nom_cmd (strcat "C:" cmd))
        (if (not (eval (read nom_cmd)))
            (eval
             (read (strcat
                    "(defun " nom_cmd "( / rtn)"
                    "(setq m:err *error* *error* *merrmsg*)"
                    "(if (ai_ffile " qapp ")"
                    "(progn (princ \"\nInitializing...\")"
                    "(_auto" quoi "load " qapp ") (setq rtn (" nom_cmd ")))"
                    "(ai_nofile " qapp "))"
                    "(setq *error* m:err m:err nil)"
                    "rtn)"
                    ))))))
   cmdliste)  nil)
(defun autoload (app cmdliste)
  (_autoqload "" app cmdliste))
(defun autoxload (app cmdliste)
  (_autoqload "x" app cmdliste))
(defun _autoload (app)
; (princ "Auto:(load ") (princ app) (princ ")") (terpri)
  (load app))
(defun _autoxload (app)
; (princ "Auto:(xload ") (princ app) (princ ")") (terpri)
  (if (= app "region") (ai_select))
  (xload app)
  (if (= app "region") (ai_amegrey "~")))
(defun ai_ffile (app)
  (or (findfile (strcat app ".lsp"))
      (findfile (strcat app ".exp"))
      (findfile (strcat app ".exe"))
      (findfile app)  ))
(defun ai_nofile (filename)
  (princ
    (strcat "\nThe file "
            filename
            "(.lsp/.exp/.exe) was not found in your search path directories."
    )  )
(princ "\nCheck the installation of the Support Files and try again.")(princ))
;;;======================== AutoLoad LISP Applications ========================
(autoload "appload" '("appload"))
(autoload "filter" '("filter"))
(autoload "dline" '("dline" "dl"))
(autoload "3d" '("3d" "ai_box" "ai_pyramid" "ai_wedge" "ai_dome"
                 "ai_mesh" "ai_sphere" "ai_cone" "ai_torus" "ai_dish"))
(autoload "ddinsert" '("ddinsert"))
(autoload "asctext" '("asctext"))
(autoload "ddattdef" '("ddattdef"))
(autoload "ddattext" '("ddattext"))
(autoload "3darray" '("3darray"))
(autoload "ddmodify" '("ddmodify"))
(autoload "ddchprop" '("ddchprop"))
(autoload "ddview" '("ddview"))
(autoload "ddvpoint" '("ddvpoint"))
(autoload "mvsetup" '("mvsetup"))
(autoload "ddosnap" '("ddosnap"))
(autoload "ddptype" '("ddptype"))
(autoload "dducsp" '("dducsp"))
(autoload "ddunits" '("ddunits"))
(autoload "ddgrips" '("ddgrips"))
(autoload "ddselect" '("ddselect"))
(autoload "ddrename" '("ddrename"))
(autoload "rman_dcl" '("rmmenu"))
(autoload "ddsolprm" '("ddsolprm"))
(autoload "plud" '("plud"))
(autoload "xplode" '("xplode"))
(autoload "dline" '("dl" "dline"))
(autoload "SPIRAL" '("SPIRAL" "3DSPIRAL"))
(autoload "RPOLY" '("RPOLY"))
(autoload "BMAKE" '("BMAKE"))
(autoload "XPLODE" '("XPLODE" "XP"))
(autoload "DDTYPE" '("DDTYPE"))
(autoload "CHTEXT" '("CHT" "chtext" "chgtext" "chgt"))
(autoload "BALLOON" '("BALLOON" "DDAN"))
(autoload "CASE" '("CASE"))
(autoload "TABLES" '("TABLES"))
(autoload "CHFACE" '("CHFACE"))
(autoload "MFACE" '("MFACE"))
(autoload "CL" '("CL"))
(autoload "PROJECT" '("PROJECT" "PROJECT1" "PROJECT2"))
(autoload "GP" '("GP"))
(autoload "arctex" '("art"))
(autoload "tline" '("tline"))
(autoload "SLOT" '("SLOT"))
(autoload "plot" '("in"))
(autoload "tuong" '("tuong" "tg"))
(autoload "otuong" '("otuong" "otg"))
(autoload "rtuong" '("rtuong" "rtg"))
(autoload "ltuong" '("ltuong"  "ltg"))
(autoload "ddxdtg" '("ddxdtg"))
(autoload "ttuong" '("ttuong"   "ttg"))
(autoload "ctuong" '("ctuong"   "ctg" "ct4"))
(autoload "gtuong" '("gtuong"   "gtg" "ct2"))
(autoload "etuong" '("etuong"   "etg"))
(autoload "ntuong" '("ntuong"   "ntg"))
(autoload "btuong" '("btuong"   "btg"))
(autoload "tgdim" '("tgdim"))
(autoload "cuamb" '("cuamb" "cmb"))
(autoload "cuamc" '("cuamc" "cmc"))
(autoload "ddcua" '("ddcua"))
(autoload "cuagm" '("cuagm"))
(autoload "cuatkh" '("cuatkh"))
(autoload "cuaskh" '("cuaskh"))
(autoload "cuatktb" '("cuatktb"))
(autoload "cuatktt" '("cuatktt"))
(autoload "cuaxoa" '("cuaxoa" "xoacua" "cx" "xc"))
(autoload "cuamk" '("cuamk"))
(autoload "cuamhm" '("cuamhm"))
(autoload "cuakn" '("cuakn"))
(autoload "cuadc" '("cuadc"))
(autoload "tmb1v" '("tmb1v"     "t1v"))
(autoload "tmb2vl" '("tmb2vl"   "t22v"))
(autoload "tmb2vc" '("tmb2vc"  "t2v"))
(autoload "tmb3v" '("tmb3v"     "t3v"))
(autoload "tmc" '("tmc"))
(autoload "ccot" '("ccot"))
(autoload "mcot" '("mcot"))
(autoload "vesan" '("vesan" "vs"))
(autoload "thuvien" '("thuvien"))
(autoload "ddkgv" '("ddkgv"))
(autoload "tdv" '("tdv"))
(autoload "utlayer" '("layset" "laymch" "laycur" "layiso" "layoff" "layfrz" "laylck" "layulk" "layon" "laythw"))
(autoload "utcolor" '("colset" "colbyl"))
(autoload "utkt" '("ktn" "ktd"))
(autoload "uttext" '("sptext" "12az" "cctext" "subtext"))
(autoload "cal" '("calc"))
(autoload "ten" '("name"))
(autoload "canchinh" '("11" "22" "33" "44" "55" "66" "77" "88" "99" "xx" "yy" "dh" "dv"))
(autoload "cot_cd" '("cot_cd"))
(autoload "cl" '("cl"))
(autoload "tline" '("tline"))
(autoload "arctext" '("ART"))
(autoload "sptext" '("sptext"))
(autoload "utot" '("mtrim" "mextend" "mprop"))
;;; ==========================================================================
(autoload "lib" '("lib"))
(autoload "dscale" '("dsc"))
(autoload "axis" '("ax1" "ax2"))
(autoload "beam" '("beam"))
(autoload "b_sec" '("b_sec"))
(autoload "node" '("joint"))
(autoload "s_sec" '("s_sec"))
(autoload "tk" '("tk_in" "tk"))
(autoload "slab" '("slab"))
(autoload "turbo" '("turbo"))
(autoload "b_lib" '("b_lib"))
(autoload "c_lib" '("c_lib"))
(autoload "fd_lib" '("fd_lib"))
(autoload "fr_lib" '("fr_lib"))
(autoload "rb_lib" '("rb_lib"))
(autoload "sl_lib" '("sl_lib"))
(autoload "sb_lib" '("sb_lib"))
(autoload "t_lib" '("t_lib"))
(autoload "offsets" '("of"))
(load "init.lsp")
;;; ========================== AUTOLOAD TGXDKT ===============================
(autoload "rman_dcl" '("rmmenu"))
(autoload "ddsolprm" '("ddsolprm"))
(autoload "ddbtkt" '("btkt"))
(autoload "ddadien" '("vd"))
(autoload "ddkcn" '("kcn"))
(autoload "lineiso" '("li"))
(autoload "circleis" '("ci"))
(autoload "dn" '("dn"))
(autoload "lap" '("ltb"))
(autoload "ten" '("name"))
(autoload "mt" '("te"))
(autoload "dm" '("cl"))
(autoload "tk_tb" '("tkcn"))
(autoload "lm" '("kh"))
(autoload "mttl" '("tt"))
(autoload "dcd" '("kcd"))
(autoload "dimc" '("dimc"))
(autoload "ct" '("at"))
(autoload "DL" '("TVDL"))
(autoload "ql" '("ql"))
(autoload "mg" '("mo"))
(autoload "uti" '("uti"))
(autoload "uti1" '("jo"))
(autoload "cal" '("calC"))
(autoload "tlv" '("tlv"))
(autoload "mdim" '("md"))
(autoload "mdimtext" '("mdt"))
(autoload "elr" '("elr"))
(autoload "ddblock" '("bltk"))
(autoload "offlr" '("tlr"))
(autoload "chlr" '("clr"))
(autoload "chblr" '("blr"))
(autoload "new_cl" '("ncl"))
(autoload "onlr" '("onl"))
(autoload "trch" '("tct"))
(autoload "tv_user" '("tvus"))
(autoload "ddcla" '("cla"))
(autoload "st" '("st"))
;;;=========================== AutoXLoad ADS Applications =======================
(autoxload "rasterin" '("gifin" "pcxin" "riaspect" "ribackg" "riedge" "rigamut" "rigrey" "rithresh" "tiffin"))
(autoxload "geomcal" '("cal"))
(autoxload "accurend" '("ar"))
(autoxload "geom3d" '("mirror3d" "rotate3d" "align"))
(autoxload "RTBV_RS4" '("RS4"))
(autoxload "geom3d" '("mirror3d" "rotate3d" "align" "mirror3d" "rotate3d" "align"))
(autoxload "hpmplot" ' ("hpconfig" "hprender" "hpmplot" "hpconfig" "hprender" "hpmplot"))

;;; ============================ COT CAO DO ================================
(defun c:ccao ()
   (if (null tl) (setq tl(getreal "\n Ti le ban ve :")) )
(setq vonglap "T")
(while (= vonglap "T")
                 (setq ddat(getpoint "\nDiem dat cot cao do :"))
(if (null ddat) (setq vonglap nil)
         (Progn  (setq h(* 4 tl))
     (setq pt1(polar  ddat  0  (- 0 (* 3 tl))                         ))
     (setq pt2(polar  pt1   0  (* 25 tl)                              ))
     (setq pt3(list   (car pt1) (+ (cadr pt1) (* 4 tl)  )             ))
     (setq pt4(list   (car pt2) (+ (cadr pt2) (* 4 tl)  )             ))
     (setq pt5(list   (car ddat) (+ (cadr ddat) (* 13 tl) )           ))
     (setq ddt(list   (+ (car ddat) tl) (+ (cadr ddat) (*  5 tl) )  ))
     (setq  p3(list   (car ddat) (+ (cadr ddat) (* 2.5 tl) )          ))
     (setq  p1(list   (+ (car p3) (* 2.5 tl) )  (cadr p3)             ))
     (setq  p2(list   (- (car p3) (* 2.5 tl) )  (cadr p3)             ))
(setq layc(getvar "clayer"))
  (taolop 7 "TRUC")
(setq txt(getstring "\nCot cao do ( 0.000 ) : "))
  (if (null txt) (setq txt "0.000"))
  (command "pline" ddat p1 p2  "close") (command "line" ddat pt5 "") (command "line" pt1 pt2 "") (command "line" pt3 pt4 "") (command "solid" p3 ddat p1 p1 "")
  (command "text" ddt h 0 (strcat "+" txt) ) (setvar "clayer" layc) )))(princ) )
;;;======================== TRUC 1->100   A->Z  =========================
(defun c:dkk ()(setq g1 (getdist "\nDuong kinh moi cho vong tron K_H cua: "))(princ))
(defun c:dkt ()(setq g (getdist "\nDuong kinh moi cho vong tron_truc : "))(princ))
(defun truc@ ()
   (vmon)
   (princ "Ky hieu <1..99>.")
   (princ "\nTL /Ky hieu cua <") 
   (if k-h null (setq k-h "/D1"))(princ k-h)(princ ">:")
   (initget 128 "TL")
   (setq k-h1 (strcase (getstring)))
	(if (= k-h1 "TL")(progn
	    (tl1)
	    (princ "\nKy hieu cua <") 
	    (if k-h null (setq k-h "/D1"))
	    (princ k-h)
	    (setq k-h1 nil)
	    (setq k-h1 (strcase (getstring ">: ")))
   			 );progn
         );if
   (if (= k-h1 "")(setq k-h1 k-h))
   (setq k-h k-h1)
   (if g1 null(setq g1 (getdist "\nDuong kinh truc:")))
   (setq cc (* g1 0.4))
   (setq pnumb (getpoint "\nDiem dat: "))

         (command "layer" "m" "truc" "c" "1" "" ""
                  "circle" pnumb "d" g1
                  "layer" "m" "text" "c" "4" "" ""
                  "text"  "j" "m" pnumb cc "0" k-h1) )
(defun truc1-0 ()	
   (princ "\nTL/Multi/Nhap Gia tri Truc <")
   (if a null (setq a 1))
   (princ a)
   (initget 128 "TL M")
   (setq num (getint ">:"))
	(if (= num "TL")(progn
	    (tl)
            (princ "\nNhap Gia tri Truc <")
	    (if a null (setq a 1))
	    (princ a)
	    (setq num nil)
	    (setq num (getint ">:"))
   			 );progn
        );if
        (if (= num "M")(progn
            (setq mt1 1 num nil)
	    (if a null (setq a 1))
            (while (/= pnumb nil)(truc1));while
            (setq mt1 nil)
                         );progn
        );if
   (if num null(setq num a)) )
(defun truc1 ()
    (princ "Truc <1...99>.")
    (if (/= mt1 1)(truc1-0))
    (if (= mt1 1)(setq num a))
    (if (= g nil)
    (setq g (getdist "\nDuong Kinh Truc:")))
    (setq cc (* g 0.45))
    (setq pnumb (getpoint "\nDiem dat: "))
    (setvar "osmode" 0)
    (if (/= mt1 1)(progn
        (setq anumb (getangle pnumb "\nPhuong truc tim: "))
        (abs anumb)
        (setq anumb1 anumb));progn
        (setq anumb anumb1));if
    (if anumb nil (setq anumb 4.71239))
    (setq tnumb (polar pnumb anumb g))
    (setq p1numb (polar pnumb anumb (/ g 2)))
   (command "layer" "m" "truc" "c" "1" "" ""
            "line" pnumb p1numb ""
             "circle" tnumb "d" g)
   (command "layer" "m" "text" "c" "4" "" ""
            "text" "j" "mc" tnumb cc "0" num)
    (setq a (+ 1 num)))
(defun truca-0 ()
    (if nh null(setq nh "a"))
    (princ "\nTL/Multi/Nhap Ky tu Truc <")
    (princ nh)
    (initget 128 "TL M")
    (setq p (strcase (getstring ">:")))
	(if (= p "TL")(progn
	    (tl)
            (princ "\nNhap Gia tri Truc <")
            (if nh null(setq nh "a"))
	    (princ nh)
	    (setq p nil)
	    (setq p (strcase (getstring ">:")))
   			 );progn
        );if
        (if (= p "M")(progn
            (setq mt1 1 p nil)
            (while (/= pnumb nil)(truca));while
            (setq mt1 nil)
                         );progn
        );if
     (if (= p "A")(setq nu 1))
     (if (= p "B")(setq nu 2))
     (if (= p "C")(setq nu 3))
     (if (= p "D")(setq nu 4))
     (if (= p "E")(setq nu 5))
     (if (= p "F")(setq nu 6))
     (if (= p "G")(setq nu 7))
     (if (= p "H")(setq nu 8))
     (if (= p "I")(setq nu 9))
     (if (= p "J")(setq nu 10))
     (if (= p "K")(setq nu 11))
     (if (= p "L")(setq nu 12))
     (if (= p "M")(setq nu 13))
     (if (= p "N")(setq nu 14))
     (if (= p "O")(setq nu 15))
     (if (= p "P")(setq nu 16))
     (if (= p "Q")(setq nu 17))
     (if (= p "R")(setq nu 18))
     (if (= p "S")(setq nu 19))
     (if (= p "T")(setq nu 20))
     (if (= p "U")(setq nu 21))
     (if (= p "V")(setq nu 22))
     (if (= p "W")(setq nu 23))
     (if (= p "X")(setq nu 24))
     (if (= p "Y")(setq nu 25))
     (if (= p "Z")(setq nu 26))
     (if (= p "")(setq nu tx)) )
(defun truca ()
    (princ "Truc <A...Z'>.")
    (if (/= mt1 1)(truca-0))
    (if (= mt1 1)(setq nu (+ nu 1)))
    (if tx null(setq tx 1))
    (if nu null (setq nu tx))
    (if (= g nil)
    (setq g (getdist "\nDuong Kinh Truc:")))
    (setq txt (substr "abcdefghiklmnopqrstuvwxyz" nu 1))
    (setq pnumb (getpoint "\nDiem dat: "))
    (setvar "osmode" 0)
    (if (/= mt1 1)(progn
        (setq anumb (getangle pnumb "\nPhuong truc tim: "))
        (abs anumb)
        (setq anumb1 anumb));progn
                (setq anumb anumb1));if
    (if anumb nil (setq anumb 4.71239))
    (setq tnumb (polar pnumb anumb g))
    (setq p1numb (polar pnumb anumb (/ g 2)))
    (setq cc (* g 0.45))
   (command "layer" "m" "truc" "c" "1" "" ""
            "line" pnumb p1numb ""
             "circle" tnumb "d" g)
   (command "layer" "m" "text" "c" "4" "" ""
            "text" "j" "mc" tnumb cc "0" txt)
    (setq tx (+ 1 nu))
    (setq nh (substr "abcdefghiklmnopqrstuvwxyz" tx 1)) (princ))
(defun c:khc () (truc@)) (defun c:tr1 () (truc1)) (defun c:tra () (truca))
;;; ============================= Xoa Cua ==================================
(defun xoacua (/ g1 g2 ss1 olderr nterr l i temp e1 e2 new old dd dc)
    (defun nterr (s)
	(command "_.UCS" "" "_.UNDO" "E")
	(setvar "cmdecho" 1)	(setvar "blipmode" 1)
	(setq g1 nil g2 nil ss1 nil e1 nil e2 nil olderr nil 
		nterr nil temp nil i nil l nil new nil old nil dd nil dc nil)
	(princ)    )
    (defun tim_in (dt / p01 p02 ktra)
	(setq p01 (cdr (assoc 10 (entget dt))))
	(setq p02 (cdr (assoc 11 (entget dt))))
	(setq ktra T)
	(if (and (> (car p01) (car g1)) (< (car p01) (car g2)) 
		 (> (cadr p01) (cadr g1)) (< (cadr p01) (cadr g2)))
	    (setq ktra nil)	)
	(if (and (> (car p02) (car g1)) (< (car p02) (car g2)) 
		 (> (cadr p02) (cadr g1)) (< (cadr p02) (cadr g2)))
	    (setq ktra nil)	)	ktra   )
   (defun timdt (dt1 dt2 / p01 p02)
	(setq p01 (cdr (assoc 10 (entget dt2))))
	(setq p02 (cdr (assoc 11 (entget dt2))))
	(setvar "ucsicon" 0)
	(command "_.UCS" "E" dt1)
	(setq p01 (trans p01 0 1))
	(setq p02 (trans p02 0 1))
	(command "_.UCS" "")
	(setvar "ucsicon" 1)
	(if (and (equal (cadr p01) 0 0.001) (equal (cadr p02) 0 0.001))
                T    nil     )   )
    (defun tim_out (dt / p01 p02 kt)
	(setq p01 (cdr (assoc 10 (entget dt))))
	(setq p02 (cdr (assoc 11 (entget dt))))
	(if (and (> (car p01) (car g1)) (< (car p01) (car g2)) 
		 (> (cadr p01) (cadr g1)) (< (cadr p01) (cadr g2)))
	    (setq kt p02)	)
	(if (and (> (car p02) (car g1)) (< (car p02) (car g2)) 
		 (> (cadr p02) (cadr g1)) (< (cadr p02) (cadr g2)))
	    (setq kt p01)	)	kt	   )
    (setvar "cmdecho" 0)
    (command "_.UNDO" "G" "_.UCS" "")
    (while (null ss1)
	(princ "\nChon cua muon xoa...")
	(initget 1)
	(setq g1 (getpoint "\n>Goc thu nhat:"))
	(initget (+ 1 32))
	(setq g2 (getcorner g1 "\n>Goc thu hai:"))
        (setq ss1 (ssget "c" g1 g2 '((0 . "LINE"))))
	(if (null ss1) (princ "\nKhong tim thay doi tuong!"))    )
        (setq temp (list (min (car g1) (car g2)) (min (cadr g1) (cadr g2)))
	  g2 (list (max (car g1) (car g2)) (max (cadr g1) (cadr g2)))
	  g1 temp)
    (setq ss1 (ssget "w" g1 g2))
    (if ss1 (command "_.ERASE" ss1 ""))
    (setq ss1 (ssget "c" g1 g2 '((0 . "LINE"))))
        (setvar "blipmode" 0)
	(setq i 0 l (sslength ss1))
	(while (< i l)
	   (if (tim_in (ssname ss1 i))
	      (progn 
		    (ssdel (ssname ss1 i) ss1)
		    (setq i 0 l (1- l))	      )	
	      (setq i (1+ i))	   )	)
	(setq l (sslength ss1))
      (while (>= l 2)
	(setq e1 (ssname ss1 0))
	(ssdel e1 ss1)
	(setq e2 nil i 0 l (sslength ss1))
	    (while (< i l) 
		(if (timdt e1 (ssname ss1 i))
		    (progn
			(setq e2 (ssname ss1 i))
		     	(setq dd (tim_out e1))
                        (setq dc (tim_out e2))    )           )
		(setq i (1+ i))	    )
	    (if e2 (progn
		        (ssdel e2 ss1)			
		        (command "_.ERASE" e2 "")
			(setq temp (entget e1))
			(setq old (assoc 10 temp))
			(setq new (cons 10 dd))
			(setq temp (subst new old temp))
			(entmod temp)
			(setq temp (entget e1))
			(setq old (assoc 11 temp))
			(setq new (cons 11 dc))
			(setq temp (subst new old temp))
			(entmod temp)
			(redraw e1)
                        (setq l (sslength ss1))  )   )	)
	(command "_.UCS" "" "_.UNDO" "E")
	(setvar "cmdecho" 1)	(setvar "blipmode" 1)        (princ) )
(defun c:cuaxoa () (xoacua))(defun c:xoacua () (xoacua))(defun c:cx     () (xoacua))(defun c:xc     () (xoacua))
;;; ============================= CHEN COT ================================
(defun c:ctr ()
(setq laycur(getvar "clayer"))
          (setq R     ( getdist "\nDuong kinh cot tron :"         ) )
          (setq Goc   ( getangle "\nGoc nghieng cua truc cot :"   ) )
(setq vonglap "T")
(while (= vonglap "T")
          (setq Tam   ( getpoint  "\nDiem chen cot:"  ) )
(if (null tam) (setq vonglap nil)
 (Progn  
          (setq p1(polar tam goc (* r 1.5) ))
          (setq p2(polar tam goc (- 0 (* r 1.5)) ) )
          (setq p3(polar tam (+ goc (/ pi 2))  (* r 1.5)       ) )
          (setq p4(polar tam (+ goc (/ pi 2))  (- 0 (* r 1.5)) ) )
(taolop 7 "Cot")
                      (command "donut" "0.0" R  tam "")
(Tim)                 (command  "line" p1 p2 ""
                                "line" p3 p4 "")   );progn
  ))(setvar "clayer" laycur)(princ) )
;;; =========================== cot vuong =================================
(defun c:ctv ()                               
(setq laycur(getvar "clayer")) (setq sna(getvar "snapang"))
(setq oth (getvar "orthomode"))
      (command "blipmode" "on") 
          (setq Goc   ( getangle "\nGoc nghieng cua truc cot :"   ) )
          (setvar "snapang" goc)  (setvar "ORTHOMODE" 1)
          (initget 7)                         ;Length can't be 0, neg, or null
          (setq dis1 (getdist  "\nDo rong Cot  : "))
          (initget 7 "Vuong")                ;Width can't be 0, neg, or null
          (setq dis2 (getdist  "\n cot Vuong/<Do dai Cot >: "))
          (if (= dis2 "Vuong") 
              (setq dis2 dis1)  )
          (setvar "ORTHOMODE" oth) (setvar "snapang" sna)
 (setq vonglap "T")
(while (= vonglap "T")
          (setq Tam   ( getpoint  "\nDiem chen cot:"  ) )
(if (null tam) (setq vonglap nil)
     (Progn  
          (setq pt  (polar tam  goc           (/ dis1 2)))
          (setq pt1 (polar pt  (+ goc (/ pi 2))  (/ dis2 2)))
          (setq pt2 (polar pt1  goc  (- 0  dis1) ))
          (grdraw pt1 pt2 2)
          (setq pt3 (polar pt2  (+ goc (/ pi 2)) (- 0 dis2) ))
          (grdraw pt2 pt3 2)
          (setq pt4 (polar pt3  goc    dis1 ))
          (grdraw pt3 pt4 2)
          (grdraw pt4 pt1 2)
(taolop 7 "Cot")
          (command "solid" pt1 pt2 pt4 pt3 "") 
          (setq po1  (polar tam  goc           (* dis1 1.5)            ))
          (setq po2  (polar tam  goc          (- 0 (* dis1 1.5))     ))
          (setq po3  (polar tam  (+ goc (/ pi 2))  (* dis2 1.5)        ))
          (setq po4  (polar tam  (+ goc (/ pi 2)) (- 0 (* dis2 1.5)) ))
(tim)     (command "line" po1 po2 ""
                   "line" po3 po4 "")   );progn
)) (command "blipmode" "off") (setvar "clayer" laycur)(princ) )
;;; ========================== CAT TUONG NUT 4 ===========================
(defun thoat () (reinit) (setq VONGLAP "Da thoat khoi chuong trinh"))
(defun c:c4 ()
 (setq vonglap "T")
 (while (= vonglap "T")
  (init)
  (setq p1 (getpoint "\n<Chon diem thu nhat>:"))
  (cond ((null p1) (thoat))
   (progn (setq p2 (getcorner p1 "\n<Chon diem thu hai>:")))  )
   (cond ((or (null p1) (null p2)) (thoat))
    (progn
     (setq taphop (ssget "c" p1 p2))
     (if (null taphop) (princ "\nTruong hop nay khong tinh
              Chi tinh hai cap doan thang song song tung doi mot")
      (progn
       (setq dem1 (sslength taphop))
       (if (/= dem1 4) (princ "\nCo nhieu hon 4 doan thang duoc chon
              Chi tinh hai cap doan thang song song tung doi mot")
       (progn
        (setq bien1 (getvar "pickbox"))
        (setvar "pickbox" 1)
;;----------PHAN NHAP LIEU-----------------
        (setq q11 (cdr (assoc 10 (entget (ssname taphop 0)))))
        (setq q12 (cdr (assoc 11 (entget (ssname taphop 0)))))
        (setq q21 (cdr (assoc 10 (entget (ssname taphop 1)))))
        (setq q22 (cdr (assoc 11 (entget (ssname taphop 1)))))
        (setq q31 (cdr (assoc 10 (entget (ssname taphop 2)))))
        (setq q32 (cdr (assoc 11 (entget (ssname taphop 2)))))
        (setq q41 (cdr (assoc 10 (entget (ssname taphop 3)))))
        (setq q42 (cdr (assoc 11 (entget (ssname taphop 3)))))
        (setq m12 (inters q11 q12 q21 q22 nil))
        (setq m13 (inters q11 q12 q31 q32 nil))
        (setq m14 (inters q11 q12 q41 q42 nil))
        (setq m23 (inters q21 q22 q31 q32 nil))
        (setq m24 (inters q21 q22 q41 q42 nil))
        (setq m34 (inters q31 q32 q41 q42 nil))
         (hacat m12 m13)  (hacat m12 m14)  (hacat m12 m23)
         (hacat m12 m24)  (hacat m12 m34)  (hacat m13 m14)
         (hacat m13 m23)  (hacat m13 m24)  (hacat m13 m34)
         (hacat m14 m23)  (hacat m14 m24)  (hacat m14 m34)
         (hacat m23 m24)  (hacat m23 m34)  (hacat m24 m34)
        (setvar "pickbox" bien1) (reinit)  ) ) ) ) ) ) )
 (princ) )
;;; ============================ CAT TUONG NUT 3 ===========================
(defun c:c3 ()
 (setq vonglap "T")
 (while (= vonglap "T")
 (init)
  (princ "\nChon tuong thu 1 can giu lai <Dung khung chon>: ")
  (setq p1 (getpoint "\n<Chon diem thu nhat>:"))
  (cond
   ((null p1) (setq vonglap "Da thoat khoi chuong trinh"))
   (progn
    (setq p2 (getcorner p1 "\n<Chon diem thu 2>:"))
    (cond
     ((null p2) (progn (princ "\nDiem khong xac dinh") (setq vonglap "T") (princ)))
     (progn
      (princ "\nChon tuong thu2 phia can giu lai <Dung khung chon>: ")
      (setq p3 (getpoint "\n<Chon diem thu 3>:"))
      (cond
       ((null p3) (princ "\nDiem khong xac dinh"))
       (progn
        (setq p4 (getcorner p3 "\n<Chon diem thu 4>:"))
        (cond
         ((null p4) (princ "\nDiem khong xac dinh"))
         (progn
          (setq taphop2 (ssget "c" p1 p2))
          (setq taphop3 (ssget "c" p3 p4))
          (if (or (null taphop2) (null taphop3))
           (princ "\n
              Chi tinh hai cap doan thang song song tung doi mot")
           (progn
            (setq dem1 (sslength taphop2))
            (setq dem2 (sslength taphop3))
            (if (or (/= dem1 2) (/= dem2 2))
             (princ "\n
              Chi tinh hai cap doan thang song song tung doi mot")
             (progn
              (setq q11 (cdr (assoc 10 (entget (ssname taphop2 0)))))
              (setq q12 (cdr (assoc 11 (entget (ssname taphop2 0)))))
              (setq q21 (cdr (assoc 10 (entget (ssname taphop2 1)))))
              (setq q22 (cdr (assoc 11 (entget (ssname taphop2 1)))))
              (setq q31 (cdr (assoc 10 (entget (ssname taphop3 0)))))
              (setq q32 (cdr (assoc 11 (entget (ssname taphop3 0)))))
              (setq q41 (cdr (assoc 10 (entget (ssname taphop3 1)))))
              (setq q42 (cdr (assoc 11 (entget (ssname taphop3 1)))))
              (if   (or
                (/= (inters q11 q12 q21 q22 nil) nil)
                (/= (inters q31 q32 q41 q42 nil) nil) )
               (princ "\n
                 Chi tinh hai cap doan thang song song tung doi mot")
               (progn
                (setq m31 (inters q31 q32 q11 q12 nil))
                (setq m32 (inters q31 q32 q21 q22 nil))
                (setq m41 (inters q41 q42 q11 q12 nil))
                (setq m42 (inters q41 q42 q21 q22 nil))
                (setq dis1 (distance p3 m31))
                (setq dis2 (distance p3 m32))
                (cond
                 ((> dis1 dis2)
                  (progn
                   (setq bien1 (getvar "pickbox"))
                   (setvar "pickbox" 1)
                   (hacat m32 m42)
                   (setq p5 (polar m32 (angle m41 m31) (/ (distance m41 m31) 3)))
                   (setq p6 (polar m32 (angle m41 m42) (/ (distance m41 m42) 3)))
                   (setq p7 (polar m42 (angle m31 m41) (/ (distance m31 m41) 3)))
                   (setq p8 (polar m42 (angle m31 m32) (/ (distance m31 m32) 3)))
                   (hauon p5 p6)
                   (hauon p7 p8)
                   (setvar "pickbox" bien1)   )  )
                 ((< dis1 dis2)
                  (progn
                   (setq bien1 (getvar "pickbox"))
                   (setvar "pickbox" 1)
                   (hacat m31 m41)
                   (setq p5 (polar m31 (angle m42 m41) (/ (distance m42 m41) 3)))
                   (setq p6 (polar m31 (angle m42 m32) (/ (distance m42 m32) 3)))
                   (setq p7 (polar m41 (angle m32 m31) (/ (distance m32 m31) 3)))
                   (setq p8 (polar m41 (angle m32 m42) (/ (distance m32 m42) 3)))
                   (hauon p5 p6)
                   (hauon p7 p8)
                   (setvar "pickbox" bien1) ) ) ) ) ) ) )))))))))))) (reinit)
 (princ) )
;;; =========================== CAT TUONG NUT 2 =============================
(defun h:uon1 (diemuon1 uv1 uv2 uv3 / ua1 ua2)
 (setq ua1 (polar diemuon1 (angle uv1 uv2) (/ (distance uv1 uv2) 3)))
 (setq ua2 (polar diemuon1 (angle uv1 uv3) (/ (distance uv1 uv3) 3)))
 (command "fillet" ua1 ua2) )
(defun h:uon2 (diemuon2 v1 v2 v3 / a1 a2)
 (setq a1 (polar diemuon2 (angle v2 v1) (/ (distance v2 v1) 3)))
 (setq a2 (polar diemuon2 (angle v3 v1) (/ (distance v3 v1) 3)))
 (command "fillet" a1 a2) )
;;truong hop 1//2 3//4
(defun goc5 (k11 k12 k21 k22 k31 k32 k41 k42
              / m13 m14 m23 m24 ds1 ds2 ds3 ds4 bien3)
 (init)
 (setq bien3 (getvar "pickbox"))
 (setvar "pickbox" 1)
 (setq m13 (inters k11 k12 k31 k32 nil))
 (setq m14 (inters k11 k12 k41 k42 nil))
 (setq m23 (inters k21 k22 k31 k32 nil))
 (setq m24 (inters k21 k22 k41 k42 nil))
 (setq ds1 (khoangcach p1 k11 k12))
 (setq ds2 (khoangcach p1 k21 k22))
 (setq ds3 (khoangcach p1 k31 k32))
 (setq ds4 (khoangcach p1 k41 k42))
 (cond
  ((< ds1 ds2)
   (progn
    (cond
     ((< ds3 ds4) (progn (h:uon1 m13 m24 m23 m14) (h:uon2 m24 m13 m23 m14)))
     ((> ds3 ds4) (progn (h:uon1 m14 m23 m24 m13) (h:uon2 m23 m14 m24 m13)))
     ((= ds3 ds4) (princ "\nKhong tinh truong hop nay")) ) ) )
  ((< ds2 ds1)
   (progn
    (cond
     ((< ds3 ds4) (progn (h:uon1 m23 m14 m24 m13) (h:uon2 m14 m23 m24 m13)))
     ((> ds3 ds4) (progn (h:uon1 m24 m13 m23 m14) (h:uon2 m13 m24 m23 m14)))
     ((= ds3 ds4) (princ "\nKhong tinh truong hop nay")) ) ) )
  ((= ds2 ds1) (princ "\nKhong tinh truong hop nay")) )
 (setvar "pickbox" bien3) )
;;
(defun thoat () (reinit) (setq vonglap "Da thoat khoi chuong trinh"))
(defun c:c2 (/ p1 p2 q11 q12 q21 q22 q31 q32 q41 q42 
               dem1 vonglap taphop1)
 (setq vonglap "TT")
 (while (= vonglap "TT")
  (init)
  (setq p1 (getpoint "\n<Chon diem thu nhat>: "))
  (cond ((null p1) (thoat))
   (progn (setq p2 (getcorner p1 "\n<Chon diem thu hai>: ")))  )
;;
  (cond ((or (null p1) (null p2)) (thoat))
   (progn
    (setq taphop1 (ssget "c" p1 p2))
    (if (null taphop1) (princ "\nTruong hop nay khong tinh
              Chi tinh hai cap doan thang song song tung doi mot")
     (progn
      (setq dem1 (sslength taphop1))
      (if (/= dem1 4) (princ "\nCo nhieu hon 4 doan thang duoc chon
              Chi tinh hai cap doan thang song song tung doi mot")
       (progn
        (setq q11 (cdr (assoc 10 (entget (ssname taphop1 0)))))
        (setq q12 (cdr (assoc 11 (entget (ssname taphop1 0)))))
        (setq q21 (cdr (assoc 10 (entget (ssname taphop1 1)))))
        (setq q22 (cdr (assoc 11 (entget (ssname taphop1 1)))))
        (setq q31 (cdr (assoc 10 (entget (ssname taphop1 2)))))
        (setq q32 (cdr (assoc 11 (entget (ssname taphop1 2)))))
        (setq q41 (cdr (assoc 10 (entget (ssname taphop1 3)))))
        (setq q42 (cdr (assoc 11 (entget (ssname taphop1 3)))))
        (cond
         ((and
           (null (inters q11 q12 q21 q22 nil))
           (null (inters q41 q42 q31 q32 nil))  )
          (goc5 q11 q12 q21 q22 q31 q32 q41 q42))
         ((and
           (null (inters q11 q12 q31 q32 nil))
           (null (inters q41 q42 q21 q22 nil))  )
          (goc5 q11 q12 q31 q32 q21 q22 q41 q42))
         ((and
           (null (inters q11 q12 q41 q42 nil))
           (null (inters q21 q22 q31 q32 nil)) )
          (goc5 q11 q12 q41 q42 q21 q22 q31 q32))
         (progn
          (princ "\nTruong hop nay khong tinh
        Chi tinh hai cap doan thang song song tung doi mot")))))))))) (princ) )
;;; =========================== VE NET CAT CHEO =============================
(defun C:G1 () (setq old_osmode (getvar "OSMODE"))
   (setq ps1 (getpoint "\nPick first point: "))
   (setq ps2 (getpoint ps1 "\nPick end point: ")) (setq sb 300.0 sh 500.0 se 1.0)
   (setq ang (angle ps1 ps2)) (setq pf1 (polar ps1 ang (- 0.0 se)))
   (setq pf2 (polar ps1 ang (/ (- (distance ps1 ps2) sb) 2.0) ))
   (setq pf3 (polar pf2 (+ ang (/ pi 2)) (/ sh 2.0)))
   (setq pf5 (polar pf2 ang sb)) (setq pf4 (polar pf5 (- ang (/ pi 2)) (/ sh 2.0)))
   (setq pf6 (polar ps2 ang se)) (setvar "OSMODE" 0) (setvar "BLIPMODE" 0)
   (command "PLINE" pf1 pf2 pf3 pf4 pf5 pf6 "")
   (setvar "OSMODE" 177) (setvar "BLIPMODE" 1)   (setvar "OSMODE" old_osmode)   (princ)   )
;============================================================================
(defun C:G0 () (setq point (getpoint "\nInsert point : "))
 (setq p1 (polar point (+ (/ pi 4) pi) 150) ) (setq p2 (polar point    (/ pi 4)     150) )
 (command "LAYER" "M" "DIM1" "C" "2" "" "") (COMMAND  "OSNAP" INT)
 (setq oldwid (getvar "PLINEWID")) (setq oldosmode (getvar "OSMODE")) (setvar "PLINEWID" 50.0) (setvar "OSMODE" 0)
 (command "PLINE" p1 point p2 "") (setvar "PLINEWID" oldwid) (setvar "OSMODE" oldosmode) (COMMAND "OSNAP" NON) (princ))
;;; ========================== Ve Hinh chu nhat ===============================
(defun HCN (/ olderr ocmd oblp pt1 pt2 pt3 pt4 l w)
  (setq ocmd (getvar "cmdecho"))
  (setq oblp (getvar "blipmode"))
  (setvar "cmdecho" 0)
  (initget 1)                         ;3D point can't be null
  (setq pt1 (getpoint (strcat "\nCorner of rectangle or square: ")))
  (setvar "ORTHOMODE" 1)
  (initget 7)                         ;Length can't be 0, neg, or null
  (setq l (getdist pt1 "\nLength: "))
  (setq pt2 (list (+ (car pt1) l) (cadr pt1) (caddr pt1)))
  (grdraw pt1 pt2 2)
  (initget 7 "Square")                ;Width can't be 0, neg, or null
  (setq w (getdist pt1 "\nSquare/<Width>: "))
  (if (= w "Square") 
      (setq w l)  )
  (setq pt3 (list (car pt2) (+ (cadr pt2) w) (caddr pt2)))
  (setq pt4 (list (car pt1) (+ (cadr pt1) w) (caddr pt1)))
  (grdraw pt2 pt3 2)
  (grdraw pt3 pt4 2)
  (grdraw pt4 pt1 2)
  (setvar "ORTHOMODE" 0)
  (command "pline"  pt1 pt2 pt3 pt4 "close")
  (setvar "cmdecho" ocmd)
  (setvar "blipmode" oblp) (princ))
(DEFUN C:HCN () (HCN)) (DEFUN C:CN () (HCN))
;;; ===============================   RECTANG  ==============================
(defun RECTANG ( / cmde pt1 pt2)   (setvar "CMDECHO" 0)
  (setq pt1 (getpoint "\nFirst corner: ")
	pt2 (getcorner pt1 "\nOther corner: ")  )
  (command "_.PLINE" pt1 (list (car pt1) (cadr pt2))
                   pt2 (list (car pt2) (cadr pt1)) "_C"  )  (princ))
(DEFUN C:RE ()      (RECTANG)) (DEFUN C:RECTANG () (RECTANG)) (PRINC)
;;; ============================= Rectang xien ==============================
(defun rec ( / cmde pt1 pt2)  (setvar "CMDECHO" 0)
  (setq oth(getvar "orthomode" ))  (setq sna(getvar "snapang" )) (command "blipmode" "on")
  (initget 1)  (setq pt1 (getpoint "\nGoc dau tien : ")) (setvar "ORTHOMODE" 0)
  (setq goc (getangle pt1 "\nGoc nghieng voi truc X : ")) 
  (setvar "snapang" goc) 
  (initget 7)  (setvar "ORTHOMODE" 1)(setq dis1 (getdist pt1 "\nDo rong hinh chu nhat : "))
  (setq pt2 (polar pt1  goc   dis1))  (grdraw pt1 pt2 2)
  (initget 7 "Vuong") (setq dis2 (getdist pt1 "\n hinh Vuong/<Do rong hinh chu nhat>: "))
  (if (= dis2 "Vuong")  (setq dis2 dis1)  )
  (setq pt4 (polar pt1 (+ goc (/ pi 2))  dis2))  (setq pt3 (polar pt4  goc              dis1))
  (command "pline" pt1 pt2 pt3 pt4 "close")  (grdraw pt2 pt3 2)  (grdraw pt3 pt4 2)  (grdraw pt4 pt1 2)
  (command "blipmode" "off")  (setvar "ORTHOMODE" oth) (setvar "snapang" sna)
  (princ))  (defun c:Rec () (rec))
;;; ============================= VE COT CAO DO ===========================
(defun c:CO (/ haicl m1 m2 pt0) (init)
 (setq haicl (getvar "clayer")) (taolop 4 "text")
 (setq m1 (getpoint "\nDiem dat cot: "))
 (setq m2 (getstring "\nNhap cot cao do <0.000>: "))
 (command "insert" "cotcaodo" m1 "100" "" "" m2)
 (setvar "clayer" haicl) (reinit) (princ))
;;; =========================== CHEN CUA 1 CANH ============================
(defun dunghinh (/ pt5)
 (setq haicl (getvar "clayer"))
 (initget 128)
 (setvar "osmode" 128)
 (setq hai (/ haid1 1000.0))
 (setq Pt1 (polar pt00 (angle pt00 pt0) haidt))
 (setq Pt3 (getpoint pt1 "\nChon vi tri tuong doi dien: "))
 (setq Pt2 (polar pt1 (angle pt00 pt0) haid1))
 (setq Pt4 (polar pt3 (angle pt00 pt0) haid1))
 (setq Pt5 (polar pt1 (angle pt3 pt1) (distance pt1 pt3)))
 (setq diemphu (polar pt1 (angle pt1 pt2) (/ haid1 2)))
 (setq diemkyhieu (polar diemphu (angle pt1 pt3) (+ (distance pt1 pt3) 400)))
 (setvar "osmode" 0)
 (setvar "clayer" (cdr (assoc 8 (entget (ssname (ssget pt0) 0)))))
 (command  "line" pt1 pt3 "" "line" pt2 pt4 "") (hacat pt1 pt2) (hacat pt3 pt4)
 (taolop 3 "CUA")
 (command "ucs" "3" pt1 pt2 pt5)
 (command "insert" "cua-di-1" "0,0" haid1 "" "")
 (command "ucs" "p")
 (setvar "clayer" haicl)
 (setq temp "T"))
;------------------CHUONG TRINH CHINH-------------------------------------
(defun c:D1 (/ temp haicl Pt0 Pt00 m0 m1 m2
               batdinh Pt1 Pt2 Pt3 Pt4 Pt5 Pt6 Pt7)
 (init)
 (command "ucs" "")
 (setq batdinh (getvar "osmode"))
 (if (null haid1) (setq haid1 900))
 (if (null haidt) (setq haidt 110))
 (setq temp "T")
 (while (= temp "T")
  (setvar "osmode" 32)
  (initget "D X K")
  (setq pt00 (getpoint "\nDo rong cua/Kich thuoc dau tuong/eXit<Goc tuong gan ban le>:"))
  (cond
   ((= pt00 "D") (setq haid1 (ha:nhap "Do rong cua" haid1)))
   ((= pt00 "K") (setq haidt (ha:nhap "Kich thuoc dau tuong" haidt)))
   ((= pt00 "X") (ha:thoat))
   ((null pt00)
    (and
     (princ "\nChon mot diem xac dinh goc tuong gan ban le")
     (setq temp "T")    )   )
   (progn
    (Init)
    (initget 128)
    (setvar "osmode" 512)
    (setq Pt0 (getpoint pt00 "\nDiem thu hai"))
    (DUNGHINH)
    (initget 32)
    (setq m2 (getstring "\nSo hieu cua D<1>: "))
    (command "insert" "sh_cuadi" diemkyhieu "100" "" "" m2)
    (reinit)
    (setq diemkyhieu nil) (setq diemphu nil)
     )  ) ) (setvar "osmode" batdinh) (command "ucs" "p") (princ))
;;; ========================== CHEN CUA 2 CANH ==============================
(defun t1 ( canh_huyen canh_ben) (setq c (* canh_huyen canh_huyen)) (setq a (* canh_ben canh_ben)) (sqrt (- c a)))
(defun d2:cua (v1 v2 v3 / py)  
 (taolop 3 "CUA") (setq Py (polar v1 (angle v3 v1) 100))
 (command "ucs" "3" v1 v2 py
          "insert" "cua-di-2" "0,0" (/ haid2 2) "" ""
          "ucs" "p"))
;;----------------------Dung hinh voi tuong thang "LINE"----------------------
(defun d2:dunghinh1 (/ hainame dis1 dis3 m)             ;Dung hinh voi tuong la "LINE"
 (setq hainame (ssname (ssget pt0) 0)
       Pt (cdr (assoc 10 (entget hainame)))
       Pt1 (polar pt0 (angle pt0 pt) (/ haid2 2))
       Pt3 (polar pt0 (angle pt pt0) (/ haid2 2))
       Pt2 (polar pt00 (angle pt0 pt) (/ haid2 2))
       Pt4 (polar pt00 (angle pt pt0) (/ haid2 2)) )
 (setq diemphu (polar pt1 (angle pt1 pt3) (/ haid2 2)))
 (setq diemkyhieu (polar diemphu (angle pt1 pt2) (+ (distance pt1 pt2) 400)))
 (setvar "clayer" (cdr (assoc 8 (entget hainame))))
 (hacat pt1 pt3) (hacat pt2 pt4)
 (command "line" pt1 pt2 "" "line" pt3 pt4 "")
 (initget 32)
 (while (null m) (progn (terpri) (setq m (getpoint pt0 "\nPhia cua mo"))))
 (setq dis1 (distance m pt0)
       dis3 (distance m pt00))
 (cond
  ((< dis1 dis3) (d2:cua pt0 pt1 pt00))
  ((> dis1 dis3) (d2:cua pt00 pt4 pt0)) ))
;;;----------------Dung hinh cua tren tuong cong "ARC"------------------------
(defun d2:dunghinh2 (p1 p2 / p01 p02 p3 p4 p5 p6
                     dis dis1 dis2 taphop1 taphop2 name1 name2)
 (setq taphop1 (ssget p1))
 (setq taphop2 (ssget p2))
 (setq name1 (ssname taphop1 0))
 (setq name2 (ssname taphop2 0))
 (setq center1 (cdr (assoc 10 (entget name1))))   ; cac thong so
 (setq center2 (cdr (assoc 10 (entget name2))))   ; ve tuong cong
 (setq r1 (cdr (assoc 40 (entget name1))))        ;
 (setq r2 (cdr (assoc 40 (entget name2))))        ;
 (setq dis1 (t1 r1 (/ haid2 2)))        
 (setq dis2 (t1 r2 (/ haid2 2)))        
 (setq p01 (polar center1 (angle center1 p1) dis1))
 (setq p02 (polar center2 (angle center2 p2) dis2))
 (setq p3 (polar p01 (- (angle p1 center1) (/ pi 2)) (/ haid2 2)))
 (setq p5 (polar p01 (+ (angle p1 center1) (/ pi 2)) (/ haid2 2)))
 (cond
  ((< r1 r2)
   (setq p4 (polar p3 (angle center1 p3) (abs (- r1 r2))))
   (setq p6 (polar p5 (angle center1 p5) (abs (- r1 r2))))  )  ((> r1 r2)
   (setq p4 (polar p3 (angle p3 center1) (abs (- r1 r2))))
   (setq p6 (polar p5 (angle p5 center1) (abs (- r1 r2))))  ) )
 (setq diemphu (polar p3 (angle p3 p5) (/ haid2 2)))
 (setq diemkyhieu (polar diemphu (angle p3 p4) (+ (distance p3 p4) 400)))
 (command "break" p3 p5 "break" p4 p6)
 (command "line" p3 p4 "" "line" p5 p6 "")
 (d2:cua p01 p3 p02) )
(defun d2:tuongcong ( p1 p2 / m ds1 ds2 p0
                      center1 center2 r1 r2
                      taphop1 taphop2 name1 name2)
 (setq p0 (polar p1 (angle p1 p2) (/ (distance p1 p2) 2)))
 (setq taphop1 (ssget p1))
 (setq taphop2 (ssget p2))
 (setq name1 (ssname taphop1 0))
 (setq name2 (ssname taphop2 0))
 (setq center1 (cdr (assoc 10 (entget name1))))   ; cac thong so
 (setq center2 (cdr (assoc 10 (entget name2))))   ; ve tuong cong
 (setq r1 (cdr (assoc 40 (entget name1))))        ;
 (setq r2 (cdr (assoc 40 (entget name2))))        ;
 (while (null m)
  (setq m (getpoint p0 "\nPhia cua mo"))
  (if (null m) (princ "\nHay xac dinh phia cua mo")
   (progn
    (setq ds1 (distance m p1))
    (setq ds2 (distance m p2))
    (cond
     ((< ds1 ds2) (d2:dunghinh2 p1 p2))
     ((> ds1 ds2) (d2:dunghinh2 p2 p1))    )   )  ) ))
;------------------------------ CHUONG TRINH CHINH --------------------------
(defun c:D2 (/ haicl hai batdinh temp 
               Pt0 Pt00 Pt1 Pt2 Pt3 Pt4)
 (setq batdinh (getvar "osmode"))
 (command "ucs" "")
 (Init)
 (if (null haid2) (setq haid2 1200))
 (setq temp "T")
 (while temp
  (setvar "osmode" 2)
  (initget "d x")
  (setq pt0 (getpoint "\nDo rong cua/eXit/<Diem giua cua>:"))
  (cond
   ((= pt0 "d") (setq haid2 (ha:nhap "Do rong cua" haid2)))
   ((= pt0 "x") (setq temp nil))
   ((null pt0) (princ "\nChon mot diem xac dinh diem giua cua"))
   (progn
    (Init)
    (setq haicl (getvar "clayer"))
    (setvar "osmode" 128)
    (setq Pt00 (getpoint pt0 "\nVi tri tuong doi dien: "))
    (setvar "osmode" 0)
    (setq name1 (cdr (assoc 0 (entget (ssname (ssget pt0) 0)))))
    (setq name2 (cdr (assoc 0 (entget (ssname (ssget pt00) 0)))))
    (cond
     ((and (= name1 "LINE") (= name2 "LINE")) (d2:dunghinh1))
     ((and (= name1 "ARC") (= name2 "ARC")) (d2:tuongcong pt0 pt00))
     (progn
      (princ "\nChuong trinh chi thuc hien duoc voi tuong la LINE hoac ARC
                Can phai explode tuong vua chon")     )    )
    (setvar "clayer" haicl)
    (initget 32)
    (setq m2 (getstring "\nSo hieu cua D<1>: "))
    (command "insert" "sh_cuadi" diemkyhieu "100" "" "" m2)
    (reinit)
    (setq diemkyhieu nil) (setq diemphu nil)
   )  ) ) (setvar "osmode" batdinh) (command "ucs" "p") (princ))
;;; ============================== CHEN CUA SO ==============================
(if (null haiwd) (setq haiwd 1200))
(defun Dorongwd (/ key)
 (princ "Do rong cua/<")
 (princ haiwd)
 (princ ">: ")
 (setq key (getint))
 (if (> key 1) (setq haiwd key)))
;;
(defun dunghinhwd (/ ds diemphu)
 (setq hai (ssget pt00))
 (setq hainame (ssname hai 0))
 (setq Pt0 (cdr (assoc 10 (entget hainame))))
 (setq Pt1 (polar pt00 (angle pt0 pt00) (/ haiwd 2)))
 (setq Pt2 (polar pt1 (angle pt1 pt0) haiwd))
 (setvar "osmode" 128)
 (setq Pt3 (getpoint pt1 "\nChon vi tri tuong doi dien: "))
 (setq Pt4 (polar pt3 (angle pt1 pt2) haiwd))
 (setq ds (/ (distance pt1 pt3) 2))
 (setq diemphu (polar pt00 (angle pt1 pt3) ds))
 (setq diemkyhieu (polar diemphu (angle pt1 pt3) (+ ds 450)))
 (setvar "osmode" 0)
 (taolop 2 "tuong")
 (command  "line" pt1 pt3 "" "line" pt2 pt4 "")
 (hacat pt1 pt2)
 (hacat pt3 pt4)
 (setq pt5 (polar pt1 (angle pt1 pt3) 40))
 (setq pt6 (polar pt2 (angle pt1 pt3) 40))
 (setq pt7 (polar pt3 (angle pt3 pt1) 40))
 (setq pt8 (polar pt4 (angle pt3 pt1) 40))
 (taolop 3 "CUA")
 (command  "line" pt5 pt6 "" "line" pt7 pt8 "" "line" pt1 pt2 "" "line" pt3 pt4 "")
 (SETQ TEMP "T") )
(defun thoatwd () (reinit) (setq Temp "Da thoat khoi chuong trinh"))
------CHUONG TRINH CHINH-----------------------------------------------------
(defun c:wd () (Init)
(setq temp "T")
(while (= temp "T")
 (setvar "osmode" 2)
 (initget "d x")
 (setq key1 (getpoint "\nDo rong cua/eXit/<Diem giua cua>: "))
 (cond
  ((= key1 "d") (dorongwd))
  ((= key1 "x") (thoatwd))
  ((null key1)
   (and
    (princ "Chon mot diem xac dinh diem giua cua")
    (setq temp "T")   )  )
  (progn
   (Init)
   (setq haicl (getvar "clayer"))
   (setq pt00 key1)
   (dunghinhwd)
   (initget 32)
   (setq m2 (getstring "\nKy hieu cua S<1>: "))
   (command "insert" "sh_cuaso" diemkyhieu "100" "" "" m2)
   (setvar "clayer" haicl)   (setq diemkyhieu nil)
   (reinit)  ) ))(princ))

;;; ============================ DRAW CLOUD =============================
(defun CLOUD (/ pt1 pt2 arc1 cnt ss la)    (setvar "cmdecho" 0)
    (prompt "\nVe cloud (may) khong khep kin - Tu khep kin ve diem dau!")
    (setq la (getvar "clayer"))
    (command "layer" "m" "cloud" "c" "5" "" "")
    (setq pt1 (getpoint "\nEnter first point of Cloud: "))
    (if pt1 (prompt "\nProceed in a COUNTER-CLOCKWISE direction..."))
    (setq cnt 1 ss (ssadd))
    (while pt1 (setq pt2 (getpoint "\nEnter next point - and close: "))
    (if pt2 (progn (command "arc" pt1 "e" pt2 "r" (/ (distance pt1 pt2) 1.75))
    (if (= cnt 1) (setq arc1 (entlast) cnt 2) (ssadd (entlast) ss)) ))
    (setq pt1 pt2) ) (setvar "highlight" 0) (if (> (sslength ss) 0)
    (command "pedit" arc1 "y" "j" ss "" "x")
    (if arc1 (command "pedit" arc1 "y" "x")) ) (setvar "highlight" 1)
    (command "layer" "s" la "")    (setvar "cmdecho" 1)    (princ))  
(DEFUN C:CLOUD () (CLOUD)) (DEFUN C:CLO () (CLOUD))
;;; ========================== FUNCTIONS  PLAN 3.0 ===========================
(DEFUN BAT_LAYER  (TEN / DS) (IF (SETQ DS (TBLSEARCH "layer" TEN)) (PROGN (IF (= (CDR (ASSOC 70 DS)) 65) (COMMAND "layer" "t" TEN "")) (IF (= (CDR (ASSOC 70 DS)) 68) (COMMAND "layer" "u" TEN "")) (IF (= (CDR (ASSOC 70 DS)) 69) (PROGN (COMMAND "layer" "t" TEN "") (COMMAND "layer" "u" TEN ""))) (IF (< (CDR (ASSOC 62 DS)) 0) (COMMAND "layer" "on" TEN ""))) (COMMAND "layer" "n" TEN "")))
(DEFUN BAT_STYLE  (TEN / DS) (SETQ DS (TBLSEARCH "STYLE" TEN)) (IF DS (IF (NOT (ZEROP (CDR (ASSOC 40 DS)))) (COMMAND "style" TEN TEN "0" "" "" "" "" "")) (COMMAND "style" TEN TEN "0" "" "" "" "" "")) (SETVAR "textstyle" TEN))
(DEFUN C:CHENKH  (/ TG PT TL) (SETVAR "cmdecho" 0) (PROGN (SETQ M:ERR *ERROR*) (PRINC)) (DEFUN *ERROR* (MSG) (PRINC MSG) (TERPRI) (SETQ *ERROR* M:ERR M:ERR nil) (PRINC) (PRINC)) (IF (NOT GAN_GT) (PROGN (TERPRI) (PROMPT "Can phai tai Start vao truoc.") (EXIT))) (SETQ KY_HIEU_MAT_CAT (GAN_GTSTR KY_HIEU_MAT_CAT "1") PT T TI_LE_VPHONG (GAN_GTSO TI_LE_VPHONG 1.0) TLE_DT (GETVAR "dimscale") SO_KY_HIEU (GAN_GTSO SO_KY_HIEU 1)) (WHILE (/= (TYPE PT) (QUOTE LIST)) (TERPRI) (INITGET 1 "Ti") (SETQ PT (GETPOINT (STRCAT "Ti le ve phong:" (RTOS TI_LE_VPHONG 2 SPHAY) "/<Diem dat>:"))) (COND ((= PT "Ti") (SETQ TI_LE_VPHONG (NHAP_KCDK0 TI_LE_VPHONG "Ti le ve phong<"))) (T nil))) (TERPRI) (SETQ TG (GETSTRING (STRCAT "Ky hieu mat cat<" KY_HIEU_MAT_CAT ">:"))) (IF (/= TG "") (SETQ KY_HIEU_MAT_CAT TG)) (SETQ TL (* TI_LE_VPHONG TLE_DT)) (COMMAND "insert" (STRCAT "kyhieu" (ITOA SO_KY_HIEU)) PT TL "" "0" KY_HIEU_MAT_CAT) (IF (= SO_KY_HIEU 4) (COMMAND KY_HIEU_MAT_CAT)) (PRINC) (PRINC))
(DEFUN CHAT_TUONG_CONG  (PT / DTAM GOC_H TG TL34 D1 D2) (SETQ D31 (TRANS (DIEM_DAU E3) E3 1) D32 (TRANS (DIEM_CUOI E3) E3 1) D41 (TRANS (DIEM_DAU E4) E4 1) GOC_VE12 (ANGLE D31 D32) GOC_H (CDR (ASSOC 42 (ENTGET (ENTNEXT E3)))) GOC_H (- GOC_VE12 GOC_H) DTAM (TIM_TAM_PL_ARC E3) BKINH3 (DISTANCE D31 DTAM) BKINH4 (DISTANCE D41 DTAM) TL34 (/ BKINH4 BKINH3) D3 (POLAR DTAM (ANGLE DTAM PT) BKINH3) D4 (POLAR DTAM (ANGLE DTAM PT) BKINH4) GOC_VE34 (- (ANGLE D3 D4) (* PI 0.5)) DS (ENTGET E4) MAU4 (CDR (ASSOC 62 DS)) LOP4 (CDR (ASSOC 8 DS))) (COMMAND "break" (LIST E3 D3) "f" (POLAR D3 GOC_VE34 (* B_CUA 0.5)) (POLAR D3 (+ PI GOC_VE34) (* B_CUA 0.5))) (SETQ E32 (ENTLAST)) (ENTDEL E32) (SETQ E31 (ENTLAST)) (ENTDEL E32) (COMMAND "break" (LIST E4 D4) "f" (POLAR D4 GOC_VE34 (* B_CUA 0.5)) (POLAR D4 (+ PI GOC_VE34) (* B_CUA 0.5))) (SETQ E42 (ENTLAST)) (ENTDEL E42) (SETQ E41 (ENTLAST)) (ENTDEL E42) (IF (AND E7 E8 E3 E4) (PROGN (IF (= KHUON_CUA "Co") (SETQ B_LUI (* 2 B_VUA)) (SETQ B_LUI B_VUA)) (SETQ D71 (TRANS (DIEM_DAU E7) E7 1) D81 (TRANS (DIEM_DAU E8) E8 1) BKINH7 (DISTANCE DTAM D71) BKINH8 (DISTANCE DTAM D81) D7 (POLAR DTAM (ANGLE D3 D4) BKINH7) D8 (POLAR DTAM (ANGLE D3 D4) BKINH8)) (COMMAND "break" (LIST E7 D7) "f" (POLAR D7 GOC_VE34 (+ (* B_CUA 0.5) (* 0.5 W_NET) B_LUI)) (POLAR D7 (+ PI GOC_VE34) (+ (* B_CUA 0.5) (* 0.5 W_NET) B_LUI))) (SETQ E72 (ENTLAST)) (ENTDEL E72) (SETQ E71 (ENTLAST)) (ENTDEL E72) (COMMAND "break" (LIST E8 D8) "f" (POLAR D8 GOC_VE34 (+ (* B_CUA 0.5) (* 0.5 W_NET) B_LUI)) (POLAR D8 (+ PI GOC_VE34) (+ (* B_CUA 0.5) (* 0.5 W_NET) B_LUI))) (SETQ E82 (ENTLAST)) (ENTDEL E82) (SETQ E81 (ENTLAST)) (ENTDEL E82) (SETQ DS (ENTGET E71) MAU7 (CDR (ASSOC 62 DS)) LOP7 (CDR (ASSOC 8 DS))))) (SETVAR "cecolor" (ITOA MAU4)) (SETVAR "clayer" LOP4) (SETVAR "plinewid" W_NET3) (COMMAND "pline" (DIEM_CUOI E31) (DIEM_CUOI E41) "") (THE_DS_PL (ENTLAST) 71 2) (THE_DS_PL (ENTLAST) 72 TT) (THE_DS_PL (ENTLAST) 73 5) (COMMAND "pline" (DIEM_DAU E32) (DIEM_DAU E42) "") (THE_DS_PL (ENTLAST) 71 2) (THE_DS_PL (ENTLAST) 72 TT) (THE_DS_PL (ENTLAST) 73 5) (SETQ D1 (TRANS (DIEM_CUOI E31) E31 1) D2 (TRANS (DIEM_DAU E32) E32 1) DXENMOI (POLAR D1 (ANGLE D1 D2) (* (DISTANCE D1 D2) 0.5))) (IF (AND E7 E8) (PROGN (SETVAR "cecolor" (ITOA MAU7)) (SETVAR "clayer" LOP7) (SETVAR "plinewid" W_NET7) (COMMAND "pline" (DIEM_CUOI E71) (DIEM_CUOI E81) "") (THE_DS_PL (ENTLAST) 71 2) (THE_DS_PL (ENTLAST) 72 TT) (THE_DS_PL (ENTLAST) 73 6) (COMMAND "pline" (DIEM_DAU E72) (DIEM_DAU E82) "") (THE_DS_PL (ENTLAST) 71 2) (THE_DS_PL (ENTLAST) 72 TT) (THE_DS_PL (ENTLAST) 73 6))) (IF HATCH (PROGN (ENTDEL HATCH) (IF (AND E7 E8) (PROGN (TO_MAT_CAT_TUONG E71 E81) (TO_MAT_CAT_TUONG E72 E82)) (PROGN (TO_MAT_CAT_TUONG E31 E41) (TO_MAT_CAT_TUONG E32 E42))))) (SETQ TUONG_CONG T))
(DEFUN CHAT_TUONG_LAM2  (PT B_CUA / SSDT SSDTT N CD E3 E4 E7 E8 TT DT DS TG1 HATCH GOC_VE34 GOC_VUONG D3 D4 HUONG_MO DAY_TUONG GOC DIEM_XEN B DM SS B_VUA SH W_NET7 MAU LOP MAU3 MAU4 LOP4 B_LUI SO DXENMOI KC_BAT) (SETQ KC_BAT B_CUA) (IF (= (TYPE KC_TRUY_BAT) (QUOTE REAL)) (IF (< KC_BAT KC_TRUY_BAT) (SETQ KC_BAT KC_TRUY_BAT))) (SETQ SSDT (SSGET "C" (POLAR PT (* 0.25 PI) KC_BAT) (POLAR PT (* 1.25 PI) KC_BAT)) E3 nil E4 nil E7 nil E8 nil HATCH nil W_NET7 nil TG (SSADD)) (IF SSDT (PROGN (SETQ N 0 CD (SSLENGTH SSDT) TT 0) (WHILE (< N CD) (SETQ DT (SSNAME SSDT N) DS (ENTGET DT)) (IF (SETQ SO (CDR (ASSOC 71 DS))) (IF (AND (> SO 0) (< SO 3)) (SETQ TG (SSADD DT TG)))) (IF (= (CDR (ASSOC 8 DS)) "GACHMATCAT") (SETQ HATCH DT)) (SETQ N (+ N 1))))) (SETQ SSDT TG N 0 CD (SSLENGTH SSDT) TT 0) (WHILE (< N CD) (SETQ DT (SSNAME SSDT N) DS (ENTGET DT)) (IF (SETQ TG (CDR (ASSOC 72 DS))) (IF (> TG 0) (SETQ TT TG N CD))) (SETQ N (+ N 1))) (IF (= TT 0) (PROMPT "Khong tim thay tuong.") (PROGN (SETQ SSDTT (SSADD) N 0 CD (SSLENGTH SSDT)) (WHILE (< N CD) (SETQ DT (SSNAME SSDT N) DS (ENTGET DT) TG (CDR (ASSOC 72 DS)) TG1 (CDR (ASSOC 73 DS))) (IF (= TG TT) (COND ((= TG1 1) (SETQ E3 DT W_NET3 (CDR (ASSOC 40 DS)))) ((= TG1 2) (SETQ E4 DT)) ((= TG1 3) (SETQ E7 DT W_NET7 (CDR (ASSOC 40 DS)))) ((= TG1 4) (SETQ E8 DT)) (T nil))) (SETQ N (+ N 1))))) (IF W_NET7 (SETQ W_NET W_NET7) (SETQ W_NET W_NET3)) (SETQ SSDT (SSGET "X" (LIST (CONS 0 "INSERT") (CONS 2 "SL_TUONG")))) (IF (NOT SSDT) (PROGN (TERPRI) (PROMPT "Chua co tuong?") (EXIT))) (SETQ N 0 CD (SSLENGTH SSDT)) (WHILE (< N CD) (SETQ DT (SSNAME SSDT N) DS (ENTGET (ENTNEXT DT))) (SETQ SH (ATOI (CDR (ASSOC 1 DS)))) (IF (= SH TT) (SETQ N CD)) (SETQ N (+ N 1))) (REPEAT 3 (SETQ DT (ENTNEXT DT))) (SETQ B_VUA (ATOF (CDR (ASSOC 1 (ENTGET DT))))) (IF (AND E3 E4) (PROGN (SETQ TG1 (CDR (ASSOC 71 (ENTGET E3)))) (COND ((= TG1 1) (CHAT_TUONG_THANG) (SETQ DXENMOI D3 TUONG_CONG nil)) ((= TG1 2) (CHAT_TUONG_CONG PT) (SETQ TUONG_CONG T)) (T nil)))) (LIST D3 D4 B_VUA TT DXENMOI))
(DEFUN CHAT_TUONG_THANG  (/ E31 E32 E41 E42 E71 E72 E81 E82) (SETQ D31 (TRANS (DIEM_DAU E3) E3 1) D32 (TRANS (DIEM_CUOI E3) E3 1) D41 (TRANS (DIEM_DAU E4) E4 1) D42 (TRANS (DIEM_CUOI E4) E4 1) GOC_VE34 (ANGLE D31 D32) GOC_VUONG (+ GOC_VE34 (* 0.5 PI)) D3 (INTERS D31 D32 PT (POLAR PT GOC_VUONG 10) nil) D4 (INTERS D41 D42 PT (POLAR PT GOC_VUONG 10) nil) DS (ENTGET E4) MAU4 (CDR (ASSOC 62 DS)) LOP4 (CDR (ASSOC 8 DS))) (COMMAND "break" (LIST E3 D3) "f" (POLAR D3 GOC_VE34 (* B_CUA 0.5)) (POLAR D3 (+ PI GOC_VE34) (* B_CUA 0.5))) (SETQ E32 (ENTLAST)) (ENTDEL E32) (SETQ E31 (ENTLAST)) (ENTDEL E32) (COMMAND "break" (LIST E4 D4) "f" (POLAR D4 GOC_VE34 (* B_CUA 0.5)) (POLAR D4 (+ PI GOC_VE34) (* B_CUA 0.5))) (SETQ E42 (ENTLAST)) (ENTDEL E42) (SETQ E41 (ENTLAST)) (ENTDEL E42) (SETQ MAU31 (CDR (ASSOC 62 (ENTGET E31))) MAU4 (CDR (ASSOC 62 (ENTGET E41))) LOP4 (CDR (ASSOC 8 (ENTGET E41)))) (IF (AND E7 E8) (PROGN (IF (= KHUON_CUA "Co") (SETQ B_LUI (* 2 B_VUA)) (SETQ B_LUI B_VUA)) (SETQ D71 (TRANS (DIEM_DAU E7) E7 1) D72 (TRANS (DIEM_CUOI E7) E7 1) D81 (TRANS (DIEM_DAU E8) E8 1) D82 (TRANS (DIEM_CUOI E8) E8 1) D7 (INTERS D71 D72 PT (POLAR PT GOC_VUONG 10) nil) D8 (INTERS D81 D82 PT (POLAR PT GOC_VUONG 10) nil)) (COMMAND "break" (LIST E7 D7) "f" (POLAR D7 (+ PI GOC_VE34) (+ (* B_CUA 0.5) B_LUI (* W_NET 0.5))) (POLAR D7 GOC_VE34 (+ (* B_CUA 0.5) B_LUI (* W_NET 0.5)))) (SETQ E72 (ENTLAST)) (ENTDEL E72) (SETQ E71 (ENTLAST)) (ENTDEL E72) (COMMAND "break" (LIST E8 D8) "f" (POLAR D8 (+ PI GOC_VE34) (+ (* B_CUA 0.5) B_LUI (* W_NET 0.5))) (POLAR D8 GOC_VE34 (+ (* B_CUA 0.5) B_LUI (* W_NET 0.5)))) (SETQ E82 (ENTLAST)) (ENTDEL E82) (SETQ E81 (ENTLAST)) (ENTDEL E82) (SETQ MAU7 (CDR (ASSOC 62 (ENTGET E71))) LOP7 (CDR (ASSOC 8 (ENTGET E71)))))) (SETVAR "cecolor" (ITOA MAU4)) (SETVAR "clayer" LOP4) (SETVAR "plinewid" W_NET3) (COMMAND "pline" (DIEM_CUOI E31) (DIEM_CUOI E41) "") (THE_DS_PL (ENTLAST) 71 1) (THE_DS_PL (ENTLAST) 72 TT) (THE_DS_PL (ENTLAST) 73 5) (COMMAND "pline" (DIEM_DAU E32) (DIEM_DAU E42) "") (THE_DS_PL (ENTLAST) 71 1) (THE_DS_PL (ENTLAST) 72 TT) (THE_DS_PL (ENTLAST) 73 5) (IF (AND E7 E8) (PROGN (SETVAR "cecolor" (ITOA MAU7)) (SETVAR "clayer" LOP7) (SETVAR "plinewid" W_NET7) (COMMAND "pline" (DIEM_CUOI E71) (DIEM_CUOI E81) "") (THE_DS_PL (ENTLAST) 71 1) (THE_DS_PL (ENTLAST) 72 TT) (THE_DS_PL (ENTLAST) 73 6) (COMMAND "pline" (DIEM_DAU E72) (DIEM_DAU E82) "") (THE_DS_PL (ENTLAST) 71 1) (THE_DS_PL (ENTLAST) 72 TT) (THE_DS_PL (ENTLAST) 73 6))) (IF HATCH (PROGN (ENTDEL HATCH) (IF (AND E7 E8) (PROGN (TO_MAT_CAT_TUONG E71 E81) (TO_MAT_CAT_TUONG E72 E82)) (PROGN (TO_MAT_CAT_TUONG E31 E41) (TO_MAT_CAT_TUONG E32 E42))))) (SETQ TUONG_THANG T))
(DEFUN CHAY_THOAT_CHOI  (/) (IF (SETQ TF (FINDFILE "tep_id.txt")) (PROGN (SETQ F (OPEN TF "w")) (CLOSE F) (IF (SETQ F (FINDFILE "thuuydd.txt")) (COMMAND "sh" (STRCAT "del " F))) (COMMAND "sh" (STRCAT "ren " TF " thuuydd.txt")) (COMMAND "sh" "del thuuydd.txt"))) (SETVAR "FILEDIA" 0) (COMMAND "quit" "y") (TERPRI) (EXIT) (TERPRI))
(DEFUN CHINH_DINH_PLINE1  (DINH E DKEO1 / DT DS PT) (SETQ DT E) (REPEAT DINH (SETQ DT (ENTNEXT DT))) (SETQ DS (ENTGET DT) DS (SUBST (CONS 10 DKEO1) (ASSOC 10 DS) DS)) (ENTMOD DS) (ENTUPD E))
(DEFUN CHINH_GIAO_NHAU  (F1 F2 / D1 D2 D3 D4 DS DTG) (SETQ D1 (CDR (ASSOC 10 (ENTGET (ENTNEXT F1)))) D1 (TRANS D1 F1 1) D2 (CDR (ASSOC 10 (ENTGET (ENTNEXT (ENTNEXT F1))))) D2 (TRANS D2 F1 1) D3 (CDR (ASSOC 10 (ENTGET (ENTNEXT F2)))) D3 (TRANS D3 F1 1) D4 (CDR (ASSOC 10 (ENTGET (ENTNEXT (ENTNEXT F2))))) D4 (TRANS D4 F1 1) DTG (INTERS D1 D2 D3 D4 nil) DS (ENTGET (ENTNEXT (ENTNEXT F1))) DS (SUBST (CONS 10 DTG) (ASSOC 10 DS) DS)) (ENTMOD DS) (ENTUPD F1) (SETQ DS (ENTGET (ENTNEXT F2)) DS (SUBST (CONS 10 DTG) (ASSOC 10 DS) DS)) (ENTMOD DS) (ENTUPD F2))
(DEFUN CHUYEN_LOAI_DUONG  (/ L_DUONG C_TM) (SETQ C_TM T) (WHILE C_TM (SETQ L_DUONG (GETSTRING (STRCAT "Loai duong moi<" LOAI_DUONG ">:"))) (COND ((= (STRCASE L_DUONG) "L") (SETQ L_DUONG "continuous")) ((= (STRCASE L_DUONG) "D") (SETQ L_DUONG "hidden")) ((= L_DUONG "") (SETQ L_DUONG LOAI_DUONG)) (T nil)) (IF (TBLSEARCH "ltype" L_DUONG) (PROGN (SETQ C_TM nil) (COMMAND "linetype" "s" L_DUONG "")) (PROGN (COMMAND "linetype" "l" L_DUONG "" "") (IF (TBLSEARCH "ltype" L_DUONG) (PROGN (SETQ C_TM nil) (COMMAND "linetype" "s" L_DUONG "")))))) (IF (/= L_DUONG LOAI_DUONG) (PROGN (NOIPLINE) (SETQ DSPT1 (LIST (CAR DSPT1)) SSENT1 nil LOAI_DUONG L_DUONG) (SETVAR "celtype" LOAI_DUONG))))
(DEFUN CONGGOP  nil (SETQ DSPT1 (APPEND (LIST ENDPT) DSPT1)) (IF SSENT1 (SETQ SSENT1 (SSADD (ENTLAST) SSENT1)) (SETQ SSENT1 (SSADD (ENTLAST)))))
(DEFUN CONGGOP_PL  nil (SETQ DSPT1 (APPEND (LIST ENDPT) DSPT1)) (IF SSENT1 (SETQ SSENT1 (SSADD (ENTLAST) SSENT1)) (SETQ SSENT1 (SSADD (ENTLAST)))))
(DEFUN DIEM_CUOI  (ETG / PTCUOI) (SETQ PTCUOI (CDR (ASSOC 10 (ENTGET (ENTNEXT (ENTNEXT ETG)))))) PTCUOI)
(DEFUN DIEM_DAU  (ETG / PTDAU) (SETQ PTDAU (CDR (ASSOC 10 (ENTGET (ENTNEXT ETG))))) PTDAU)
(DEFUN GAN_GT  (GIA_TRI TRISO) (IF (NOT GIA_TRI) (SETQ GIA_TRI TRISO)) GIA_TRI)
(DEFUN GAN_GTSO  (BIEN GT /) (IF BIEN (IF (AND (/= (TYPE BIEN) (QUOTE REAL)) (/= (TYPE BIEN) (QUOTE INT))) (SETQ BIEN GT)) (SETQ BIEN GT)) BIEN)
(DEFUN GAN_GTSTR  (BIEN GT /) (IF BIEN (IF (/= (TYPE BIEN) (QUOTE STR)) (SETQ BIEN GT)) (SETQ BIEN GT)) BIEN)
(DEFUN GIAO_DIEM_THUC_0  (D1 D2 D3 D4 / TG) (IF (NOT (SETQ TG (INTERS D1 D2 D3 D4 T))) (SETQ TG (INTERS D1 D2 D3 D4 nil))) TG)
(DEFUN GOC_CHAN_PL_ARC  (DT / DS GOC GOC1) (SETQ DS (ENTGET (ENTNEXT DT)) GOC (CDR (ASSOC 42 DS)) GOC1 (ABS GOC) GOC1 (ATAN GOC1) GOC1 (- (* 0.5 PI) GOC1) GOC1 (- PI GOC1 GOC1) GOC1 (* GOC1 2)) (IF (< GOC 0) (SETQ GOC1 (* -1 GOC1))) GOC1)
(DEFUN HC_NOI_TUONG_THANG  (E1 E2 E3 E4 / D11 D12 D21 D22 D31 D32 D41 D42 CHUADUOC GD13 GD14 GD23 GD24 SSONG DG) (SETQ SSONG nil CHACHAI nil D11 (TRANS (DIEM_DAU E1) E1 1) D12 (TRANS (DIEM_CUOI E1) E1 1) D21 (TRANS (DIEM_DAU E2) E2 1) D22 (TRANS (DIEM_CUOI E2) E2 1) D31 (TRANS (DIEM_DAU E3) E3 1) D32 (TRANS (DIEM_CUOI E3) E3 1) D41 (TRANS (DIEM_DAU E4) E4 1) D42 (TRANS (DIEM_CUOI E4) E4 1) CHUADUOC T GD13 nil GD14 nil GD23 nil GD24 nil) (IF (NOT (ZEROP (SIN (- (ANGLE D11 D12) (ANGLE D31 D32))))) (PROGN (SETQ GD13 (GIAO_DIEM_THUC_0 D11 D12 D31 D32) GD14 (GIAO_DIEM_THUC_0 D11 D12 D41 D42) GD23 (GIAO_DIEM_THUC_0 D21 D22 D31 D32) GD24 (GIAO_DIEM_THUC_0 D21 D22 D41 D42) DG (GIAO_DIEM_THUC_0 GD13 GD24 GD23 GD14)) (IF CHUADUOC (SETQ CHUADUOC (HIEU_CHINH_CHAC3))) (IF CHUADUOC (SETQ CHUADUOC (HIEU_CHINH_CHAC2))))) (NOT CHUADUOC))
(DEFUN HIEU_CHINH_CHAC2  (/) (SETQ DG1 (POLAR D11 (ANGLE D11 D12) (/ (DISTANCE D11 D12) 2.0))) (SETQ DG3 (POLAR D31 (ANGLE D31 D32) (/ (DISTANCE D31 D32) 2.0))) (IF (> (DISTANCE DG1 GD13) (DISTANCE DG1 GD14)) (SETQ TG E3 E3 E4 E4 TG)) (IF (> (DISTANCE DG3 GD13) (DISTANCE DG3 GD23)) (SETQ TG E1 E1 E2 E2 TG)) (SETQ D11 (TRANS (DIEM_DAU E1) E1 1) D12 (TRANS (DIEM_CUOI E1) E1 1) D21 (TRANS (DIEM_DAU E2) E2 1) D22 (TRANS (DIEM_CUOI E2) E2 1) D31 (TRANS (DIEM_DAU E3) E3 1) D32 (TRANS (DIEM_CUOI E3) E3 1) D41 (TRANS (DIEM_DAU E4) E4 1) D42 (TRANS (DIEM_CUOI E4) E4 1)) (SETQ GD13 (GIAO_DIEM_THUC_0 D11 D12 D31 D32) GD14 (GIAO_DIEM_THUC_0 D11 D12 D41 D42) GD23 (GIAO_DIEM_THUC_0 D21 D22 D31 D32) GD24 (GIAO_DIEM_THUC_0 D21 D22 D41 D42)) (THAYTHE2 E1 GD13 GD14) (THAYTHE2 E2 GD24 GD24) (THAYTHE2 E3 GD13 GD23) (THAYTHE2 E4 GD24 GD24) (SETQ CHUADUOC nil CHACHAI T) CHUADUOC)
(DEFUN HIEU_CHINH_CHAC3  (/) (IF (AND (/= (ANGLE GD23 D21) (ANGLE GD23 D22)) (/= (ANGLE GD24 D21) (ANGLE GD24 D22)) (/= (ANGLE GD13 D11) (ANGLE GD13 D12)) (/= (ANGLE GD14 D11) (ANGLE GD14 D12))) (PROGN (IF (OR (INTERS DG D42 D21 D22 T) (INTERS DG D41 D21 D22 T)) (PROGN (THAYTHE3 E3 GD23 DG) (THAYTHE3 E4 GD24 DG) (COMMAND "break" (LIST E2 GD23) GD24) (SETQ CHUADUOC nil))) (IF (OR (INTERS DG D42 D11 D12 T) (INTERS DG D41 D11 D12 T)) (PROGN (THAYTHE3 E3 GD13 DG) (THAYTHE3 E4 GD14 DG) (COMMAND "break" (LIST E1 GD13) GD14) (SETQ CHUADUOC nil))))) (IF (AND (/= (ANGLE GD23 D31) (ANGLE GD23 D32)) (/= (ANGLE GD13 D31) (ANGLE GD13 D32)) (/= (ANGLE GD24 D31) (ANGLE GD24 D32)) (/= (ANGLE GD14 D31) (ANGLE GD14 D32)) CHUADUOC) (PROGN (IF (OR (INTERS DG D21 D31 D32 T) (INTERS DG D22 D31 D32 T)) (PROGN (THAYTHE3 E1 GD13 DG) (THAYTHE3 E2 GD23 DG) (COMMAND "break" (LIST E3 GD13) GD23) (SETQ CHUADUOC nil))) (IF (OR (INTERS DG D21 D41 D42 T) (INTERS DG D22 D41 D42 T)) (PROGN (THAYTHE3 E1 GD14 DG) (THAYTHE3 E2 GD24 DG) (COMMAND "break" (LIST E4 GD14) GD24) (SETQ CHUADUOC nil))))) CHUADUOC)
(DEFUN KHAI_THUOC_TINH  (TEN GTRI /) (COMMAND "attdef" "" TEN "" GTRI (LIST 0 0) "0.0001" "0") (ENTLAST))
(DEFUN KHO_GIAY  (X Y / TL) (SETVAR "cmdecho" 0) (SETQ TL (GETVAR "dimscale") X (* X TL) Y (* Y TL)) (COMMAND "pline" (QUOTE (0 0)) (LIST X 0) (LIST X Y) (LIST 0 Y) "c") (COMMAND "zoom" "e"))
(DEFUN KIEM_NGHIEM_ID  (/ CU_CHUOI N) (IF (= CACH 1) (SETQ F (FINDFILE "adfor.mbt")) (SETQ F (FINDFILE "adforf.mbt"))) (IF F (SETQ F (OPEN F "r")) (CHAY_THOAT_CHOI)) (IF (AND F IDE_DOC) (PROGN (WHILE (= (SUBSTR IDE_DOC 1 1) " ") (SETQ IDE_DOC (SUBSTR IDE_DOC 2))) (SETQ TG (SUBSTR IDE_DOC 1 1) N 2 CD_IDE (STRLEN IDE_DOC)) (WHILE (AND (<= N CD_IDE) (/= (SUBSTR IDE_DOC N 1) " ")) (SETQ TG (STRCAT TG (SUBSTR IDE_DOC N 1))) (SETQ N (+ N 1))) (SETQ IDE_DOC TG) (SETQ CD_IDE (STRLEN IDE_DOC) N 0) (WHILE (< N (+ CD_IDE 13)) (IF (SETQ DONGCC (READ-LINE F)) (PROGN (IF (= N 1) (SETQ DONG_NAME DONGCC)) (IF (= N 3) (SETQ DONG_CQ DONGCC)) (SETQ N (+ N 1))) (CHAY_THOAT_CHOI))) (SETQ CD (STRLEN IDE_DOC) N 1) (WHILE (<= N CD) (IF (SETQ TG (READ-LINE F)) (PROGN (SETQ KY_TU (SUBSTR IDE_DOC N 1) KY_TU (+ (ASCII KY_TU) 5) KY_TU (CHR KY_TU)) (SETQ CD1 (+ (ASCII KY_TU) 7) KY_TU_DOC (SUBSTR TG (+ CD1 1) 1)) (IF (/= KY_TU KY_TU_DOC) (CHAY_THOAT_CHOI))) (CHAY_THOAT_CHOI)) (SETQ N (+ N 1))) (SETQ N 1) (WHILE (READ-LINE F) (SETQ N (+ N 1))) (CLOSE F) (IF (/= N 21) (CHAY_THOAT_CHOI))) (CHAY_THOAT_CHOI)))
(DEFUN KIEM_NGHIEM_ID1  (/ CU_CHUOI N IDE_GHI TG) (WHILE (= (SUBSTR IDE_DOC 1 1) " ") (SETQ IDE_DOC (SUBSTR IDE_DOC 2))) (SETQ TG (SUBSTR IDE_DOC 1 1) N 2 CD_IDE (STRLEN IDE_DOC)) (WHILE (AND (<= N CD_IDE) (/= (SUBSTR IDE_DOC N 1) " ")) (SETQ TG (STRCAT TG (SUBSTR IDE_DOC N 1))) (SETQ N (+ N 1))) (SETQ IDE_DOC TG IDE_GHI "335505561667") (IF (/= (STRCASE IDE_GHI) (STRCASE IDE_DOC)) (CHAY_THOAT_CHOI)))
(DEFUN NET_DAY  nil (SETVAR "cecolor" MAU_W_NET) (SETVAR "plinewid" W_NET))
(DEFUN NET_MANH  nil (SETVAR "cecolor" MAU_NET0) (SETVAR "plinewid" 0))
(DEFUN NHAN_BIEN_CU  (/) (SETQ OLDCOLOR (GETVAR "cecolor") OLDOSN (GETVAR "osmode") OLDPLN (GETVAR "plinewid") OLDTHICK (GETVAR "thickness") OLDLAYER (GETVAR "clayer") OLDELEV (GETVAR "elevation")))
(DEFUN NHAP_CO_KHONG  (BIEN NHAC / TG) (TERPRI) (INITGET "Co Khong") (SETQ TG (GETKWORD (STRCAT NHAC BIEN ">:"))) (IF TG (SETQ BIEN TG)) BIEN)
(DEFUN NHAP_KCD  (SO_NHAP DONG_NHAC / SO_NHAP1) (TERPRI) (INITGET 4) (PROMPT (STRCAT DONG_NHAC (RTOS SO_NHAP DONVI SPHAY) ">:")) (SETQ SO_NHAP1 (GETDIST)) (IF SO_NHAP1 (SETQ SO_NHAP SO_NHAP1)) SO_NHAP)
(DEFUN NHAP_KCDK0  (BIEN NHAC / TG) (TERPRI) (PROMPT (STRCAT NHAC (RTOS BIEN 2 SPHAY) ">:")) (INITGET 6) (SETQ TG (GETDIST)) (IF TG (SETQ BIEN TG)) BIEN)
(DEFUN NHAP_LOAI_CUA  (TEN_LOAI_CUA NHAC / TG) (INITGET "Chunhat Vom") (SETQ TG (GETKWORD (STRCAT NHAC TEN_LOAI_CUA ">:"))) (IF TG (SETQ TEN_LOAI_CUA TG)) TEN_LOAI_CUA)
(DEFUN NHAP_RONG  (/ STW1) (TERPRI) (INITGET 4) (SETQ STW1 (GETDIST STPT (STRCAT "Starting width<" (RTOS ENDW DON_VI SPHAY) ">:"))) (IF STW1 (SETQ STW STW1) (SETQ STW ENDW)) (TERPRI) (INITGET 4) (SETQ STW1 (GETDIST STPT (STRCAT "Ending width<" (RTOS STW DON_VI SPHAY) ">:"))) (IF STW1 (SETQ ENDW STW1) (SETQ ENDW STW)))
(DEFUN NHAP_SO_HIEU  (SH NHAC / SH1) (SETQ SH (ATOI SH)) (INITGET 4) (SETQ SH1 (GETINT (STRCAT NHAC (ITOA SH) ">:"))) (IF SH1 (SETQ SH SH1)) (ITOA SH))
(DEFUN NHAP_SO_NGUYEND  (BIEN NHAC / TG) (IF (= (TYPE BIEN) (QUOTE REAL)) (SETQ BIEN (FIX BIEN))) (TERPRI) (INITGET 4) (SETQ TG (GETINT (STRCAT NHAC (ITOA BIEN) ">:"))) (IF TG (SETQ BIEN TG)) BIEN)
(DEFUN NHAP_SO_NGUYENDK0  (BIEN NHAC / TG) (IF (= (TYPE BIEN) (QUOTE REAL)) (SETQ BIEN (FIX BIEN))) (TERPRI) (INITGET 6) (SETQ TG (GETINT (STRCAT NHAC (ITOA BIEN) ">:"))) (IF TG (SETQ BIEN TG)) BIEN)
(DEFUN NHAP_SO_THUC  (SO_NHAP DONG_NHAC / SO_NHAP1) (TERPRI) (PROMPT (STRCAT DONG_NHAC (RTOS SO_NHAP DONVI SPHAY) ">:")) (SETQ SO_NHAP1 (GETREAL)) (IF SO_NHAP1 (SETQ SO_NHAP SO_NHAP1)) SO_NHAP)
(DEFUN NHAP_SO_THUCD  (SO_NHAP DONG_NHAC / SO_NHAP1) (TERPRI) (PROMPT (STRCAT DONG_NHAC (RTOS SO_NHAP DONVI SPHAY) ">:")) (INITGET 4) (SETQ SO_NHAP1 (GETREAL)) (IF SO_NHAP1 (SETQ SO_NHAP SO_NHAP1)) SO_NHAP)
(DEFUN NHAP_SO_THUCDK0  (SO_NHAP DONG_NHAC / SO_NHAP1) (TERPRI) (PROMPT (STRCAT DONG_NHAC (RTOS SO_NHAP DONVI SPHAY) ">:")) (INITGET 6) (SETQ SO_NHAP1 (GETREAL)) (IF SO_NHAP1 (SETQ SO_NHAP SO_NHAP1)) SO_NHAP)
(DEFUN NHAP_STRING  (TEN_NHAP DONG_NHAC / TEN_NHAP1) (TERPRI) (PROMPT (STRCAT DONG_NHAC TEN_NHAP ">:")) (SETQ TEN_NHAP1 (GETSTRING)) (IF (/= TEN_NHAP1 "") (SETQ TEN_NHAP TEN_NHAP1)) TEN_NHAP)
(DEFUN NHAP_STRING1  (TEN_NHAP DONG_NHAC / TEN_NHAP1) (TERPRI) (PROMPT (STRCAT DONG_NHAC TEN_NHAP ">:")) (SETQ TEN_NHAP1 (GETSTRING T)) (IF (/= TEN_NHAP1 "") (SETQ TEN_NHAP TEN_NHAP1)) TEN_NHAP)
(DEFUN NOIPLINE  (/ SODT SODIEM) (IF SSENT1 (SETQ SODT (SSLENGTH SSENT1) N 1) (SETQ SODT 0)) (IF (> SODT 1) (PROGN (COMMAND "pedit" (SSNAME SSENT1 0) "j") (WHILE (< N SODT) (COMMAND (SSNAME SSENT1 N)) (SETQ N (+ N 1))) (COMMAND "" ""))))
(DEFUN SLBR_OK  nil (SETQ DONG_CT1 (GET_TILE "dong_ct")) (SETQ DIM_POS (DONE_DIALOG 1)))
(DEFUN SUA_GHI_CHU  (DONG_TIT DONG_CT1) (SETQ DIM_POS (QUOTE (-1 -1))) (IF (NOT DI_DCL_GHI_CHU) (SETQ DI_DCL_GHI_CHU (LOAD_DIALOG "xdung.dcl"))) (IF (< DI_DCL_GHI_CHU 0) (EXIT)) (IF (NOT (NEW_DIALOG "chu_thich" DI_DCL_GHI_CHU "" DIM_POS)) (EXIT)) (SET_TILE "dong_tit" DONG_TIT) (SET_TILE "dong_ct" DONG_CT1) (ACTION_TILE "accept" "\n     (slbr_ok)") (START_DIALOG) DONG_CT1)
(DEFUN TAO_KHOI_SO_LIEU_SAN  (/ PT SS) (SETQ PT (QUOTE (0 0 0)) SS (SSADD)) (COMMAND "attdef" "i" "" "sh_san" "" "1" PT 0.0001 "0") (SETQ SS (SSADD (ENTLAST) SS)) (COMMAND "attdef" "" "day_san" "" "1200" PT 0.0001 "0") (SETQ SS (SSADD (ENTLAST) SS)) (COMMAND "attdef" "" "Ghi_chu" "" "San" PT 0.0001 "0") (SETQ SS (SSADD (ENTLAST) SS)) (COMMAND "attdef" "" "du_tru" "" "0" PT 0.0001 "0") (SETQ SS (SSADD (ENTLAST) SS)) (COMMAND "attdef" "i" "" "du_tru" "" "0" PT 0.0001 "0") (ENTDEL (ENTLAST)) (COMMAND "block" "sl_san" PT SS ""))
(DEFUN TAO_KHOI_SO_LIEU_TRU  (/ PT SS) (SETQ PT (QUOTE (0 0 0)) SS (SSADD)) (COMMAND "attdef" "i" "" "sh_tru" "" "1" PT 0.0001 "0") (SETQ SS (SSADD (ENTLAST) SS)) (COMMAND "attdef" "" "vl_tru" "" "Be tong" PT 0.0001 "0") (SETQ SS (SSADD (ENTLAST) SS)) (COMMAND "attdef" "" "Ghi_chu" "" "Cot A1" PT 0.0001 "0") (SETQ SS (SSADD (ENTLAST) SS)) (COMMAND "attdef" "" "du_tru" "" "0" PT 0.0001 "0") (SETQ SS (SSADD (ENTLAST) SS)) (COMMAND "attdef" "i" "" "du_tru" "" "0" PT 0.0001 "0") (ENTDEL (ENTLAST)) (COMMAND "block" "sl_tru" PT SS ""))
(DEFUN TAO_LOP_OFF  (TEN / DS) (IF (SETQ DS (TBLSEARCH "layer" TEN)) (PROGN (IF (= (CDR (ASSOC 70 DS)) 65) (COMMAND "layer" "t" TEN "")) (IF (= (CDR (ASSOC 70 DS)) 68) (COMMAND "layer" "u" TEN "")) (IF (= (CDR (ASSOC 70 DS)) 69) (PROGN (COMMAND "layer" "t" TEN "") (COMMAND "layer" "u" TEN ""))) (IF (> (CDR (ASSOC 62 DS)) 0) (COMMAND "layer" "off" TEN ""))) (COMMAND "layer" "n" TEN "off" TEN "")))
(DEFUN TD_THEO_CACH1  (/ TF N CD) (SETQ THU_HANG nil THOA_MAN_CUOC_CHOI nil) (IF (NOT (SETQ TF (FINDFILE "render.exe"))) (CHAY_THOAT_CHOI)) (IF (SETQ F (OPEN "tep_id.txt" "r")) (PROGN (CLOSE F) (COMMAND "sh" "del tep_id.txt"))) (COMMAND "sh" (STRCAT TF " " (ITOA 23011986))) (IF (NOT (FINDFILE "tep_id.txt")) (CHAY_THOAT_CHOI)) (IF (SETQ F (OPEN "tep_id.txt" "r")) (PROGN (SETQ IDE_DOC (READ-LINE F)) (CLOSE F) (WHILE (= (SUBSTR IDE_DOC 1 1) " ") (SETQ IDE_DOC (SUBSTR IDE_DOC 2))) (KIEM_NGHIEM_ID)) (CHAY_THOAT_CHOI)) (SETQ TENKT (SUBSTR (GETVAR "acadprefix") 1 2) TF (FINDFILE "acadid.exe")) (IF (NOT TF) (PROGN (CHAY_THOAT_CHOI) (EXIT))) (COMMAND "sh" (STRCAT TF " > tep_id.txt")) (IF (NOT (FINDFILE "tep_id.txt")) (CHAY_THOAT_CHOI)) (IF (= (STRCASE TENKT) "D:") (SETQ SO_LAN 39) (SETQ SO_LAN 20)) (IF (NOT (FINDFILE "tep_id.txt")) (CHAY_THOAT_CHOI)) (IF (SETQ F (OPEN "tep_id.txt" "r")) (PROGN (REPEAT SO_LAN (READ-LINE F)) (SETQ IDE_DOC (READ-LINE F)) (CLOSE F) (SETQ IDE_DOC (SUBSTR IDE_DOC 24)) (WHILE (= (SUBSTR IDE_DOC 1 1) " ") (SETQ IDE_DOC (SUBSTR IDE_DOC 2))) (SETQ F (OPEN "tep_id.txt" "w")) (CLOSE F) (COMMAND "sh" "ren tep_id.txt cctao.txt") (COMMAND "sh" "del cctao.txt") (KIEM_NGHIEM_ID)) (CHAY_THOAT_CHOI)) (SETQ THU_HANG T THOA_MAN_CUOC_CHOI T))
(DEFUN TD_THEO_CACH2  nil (COMMAND "sh" "vol > tep_id.txt") (SETQ SO_LAN 2) (IF (SETQ F (OPEN "tep_id.txt" "r")) (PROGN (REPEAT SO_LAN (READ-LINE F)) (SETQ IDE_DOC (READ-LINE F)) (CLOSE F) (SETQ IDE_DOC (SUBSTR IDE_DOC 25)) (WHILE (= (SUBSTR IDE_DOC 1 1) " ") (SETQ IDE_DOC (SUBSTR IDE_DOC 2))) (SETQ F (OPEN "tep_id.txt" "w")) (CLOSE F) (COMMAND "sh" "ren tep_id.txt cctao.txt") (COMMAND "sh" "del cctao.txt") (KIEM_NGHIEM_ID)) (CHAY_THOAT_CHOI)) (SETQ THU_HANG T THOA_MAN_CUOC_CHOI T))
(DEFUN THAYTHE2  (DT D1 D2 / DDAU DSD TG) (SETQ DSD (ENTGET (ENTNEXT DT)) DDAU (TRANS (CDR (ASSOC 10 DSD)) DT 1) DSC (ENTGET (ENTNEXT (ENTNEXT DT))) DCUOI (TRANS (CDR (ASSOC 10 DSC)) DT 1)) (IF (< (DISTANCE D2 DDAU) (DISTANCE D2 DCUOI)) (PROGN (SETQ DS (ENTGET (ENTNEXT DT)) DS (SUBST (CONS 10 D1) (ASSOC 10 DS) DS)) (ENTMOD DS)) (PROGN (SETQ DS (ENTGET (ENTNEXT (ENTNEXT DT))) DS (SUBST (CONS 10 D1) (ASSOC 10 DS) DS)) (ENTMOD DS))) (ENTUPD DT))
(DEFUN THAYTHE3  (DT D1 DG / DDAU DSD TG) (SETQ DDAU (TRANS (DIEM_DAU DT) DT 1) DCUOI (TRANS (DIEM_CUOI DT) DT 1)) (IF (< (DISTANCE DG DDAU) (DISTANCE DG DCUOI)) (PROGN (SETQ DS (ENTGET (ENTNEXT DT)) DS (SUBST (CONS 10 D1) (ASSOC 10 DS) DS)) (ENTMOD DS) (ENTUPD DT)) (PROGN (SETQ DS (ENTGET (ENTNEXT (ENTNEXT DT))) DS (SUBST (CONS 10 D1) (ASSOC 10 DS) DS)) (ENTMOD DS) (ENTUPD DT))))
(DEFUN THDOI_STYLE_PFB  (KIEU FONTS / TSENT N CD ENT TEN) (SETVAR "cmdecho" 0) (SETQ M:ERR *ERROR*) (PRINC) (DEFUN *ERROR* (MSG) (PRINC MSG) (TERPRI) (SETQ *ERROR* M:ERR M:ERR nil) (PRINC)) (TERPRI) (PROMPT "Chon cac dong chu can doi kieu:") (SETQ TSENT (SSGET)) (IF TSENT (PROGN (IF (NOT (TBLSEARCH "STYLE" KIEU)) (COMMAND "style" KIEU FONTS "" "" "" "" "")) (SETQ N 0 CD (SSLENGTH TSENT)) (WHILE (< N CD) (SETQ ENT (SSNAME TSENT N) TEN (TS_T2 0 ENT)) (IF (= TEN "TEXT") (THAY_T2 7 KIEU ENT)) (SETQ N (+ N 1))))) (SETQ *ERROR* M:ERR M:ERR nil) (PRINC) (PRINC))
(DEFUN THE_DS_PL  (DT COT GT / DS) (IF DT (PROGN (SETQ DS (ENTGET DT) DS (SUBST (CONS COT GT) (ASSOC COT DS) DS)) (ENTMOD DS) (ENTUPD DT))))
(DEFUN TIM_SO_HIEU_PLAN  (SHT KHOI / SS N CD SH DS DT) (IF (/= (TYPE SHT) (QUOTE INT)) (PROGN (SETQ SS (SSGET "X" (LIST (CONS 0 "INSERT") (CONS 2 KHOI))) SHT 0) (IF SS (PROGN (SETQ N 0 CD (SSLENGTH SS) SH 0) (WHILE (< N CD) (SETQ DT (SSNAME SS N)) (IF DT (PROGN (SETQ DS (ENTGET (ENTNEXT DT))) (IF (= (CDR (ASSOC 0 DS)) "ATTRIB") (PROGN (SETQ SH (ATOI (CDR (ASSOC 1 DS)))) (IF (> SH SHT) (SETQ SHT SH)))))) (SETQ N (+ N 1)))) (SETQ SHT 0)))) SHT)
(DEFUN TIM_TAM_PL_ARC  (DT / DS GOC1 GOC2 D1 D2 KC DTAM DD) (SETQ DS (ENTGET (ENTNEXT DT)) D1 (TRANS (DIEM_DAU DT) DT 1) D2 (TRANS (DIEM_CUOI DT) DT 1) GOC1 (ANGLE D1 D2) KC (* (DISTANCE D1 D2) 0.5 (CDR (ASSOC 42 DS))) D2 (POLAR D1 GOC1 (* (DISTANCE D1 D2) 0.5)) DD (POLAR D2 (- GOC1 (* 0.5 PI)) KC) GOC1 (ANGLE D1 DD) GOC2 (- (ANGLE DD D2) (ANGLE DD D1)) GOC2 (- GOC1 GOC2) DTAM (INTERS DD D2 D1 (POLAR D1 (+ GOC2 PI) 3) nil)) DTAM)
(DEFUN TRA_BIEN_CU  (/) (MAPCAR (QUOTE SETVAR) (LIST "cecolor" "osmode" "thickness" "clayer" "elevation" "plinewid") (LIST OLDCOLOR OLDOSN OLDTHICK OLDLAYER OLDELEV OLDPLN)))
(DEFUN VE_CUNG_TRON  (/ DIEMHUONG DIEMCUOI VECT) (SETQ VECT T) (SETQ STPT (CAR DSPT1)) (WHILE VECT (TERPRI) (INITGET "Line End Direction Undo Close Width So") (SETQ ENDPT (GETPOINT STPT "diem So bo/Line/End point/Direction/Close/Width/Undo/<Second point>:")) (COND ((= (TYPE ENDPT) (QUOTE LIST)) (SETQ STPT (CAR DSPT1)) (COMMAND "pline" STPT "w" STW ENDW "a" "s" ENDPT) (PROMPT "End point:") (COMMAND PAUSE "") (SETQ STW ENDW) (SETQ ENDPT (CDR (ASSOC 10 (ENTGET (ENTNEXT (ENTNEXT (ENTLAST))))))) (CONGGOP) (SETQ STPT (CAR DSPT1))) ((NOT ENDPT) (SETQ VEDT nil VECT nil)) ((= ENDPT "Close") (SETQ SODIEM (LENGTH DSPT1) DIEMCUOI (NTH (- SODIEM 1) DSPT1)) (COMMAND "pline" STPT "a" DIEMCUOI "") (CONGGOP) (SETQ VEDT nil VECT nil)) ((= ENDPT "Width") (NHAP_RONG)) ((= ENDPT "Undo") (IF (> (LENGTH DSPT1) 1) (PROGN (SETQ SSENT1 (SSDEL (ENTLAST) SSENT1) DSPT1 (CDR DSPT1)) (SETQ STPT (CAR DSPT1)) (ENTDEL (ENTLAST))))) ((= ENDPT "Line") (SETQ VECT nil)) ((= ENDPT "End") (SETQ STPT (CAR DSPT1)) (COMMAND "pline" STPT "w" STW ENDW "a") (TERPRI) (PROMPT "End point:") (COMMAND PAUSE "") (SETQ STW ENDW) (SETQ ENDPT (CDR (ASSOC 10 (ENTGET (ENTNEXT (ENTNEXT (ENTLAST))))))) (CONGGOP) (SETQ STPT (CAR DSPT1))) ((= ENDPT "Direction") (SETQ STPT (CAR DSPT1)) (TERPRI) (SETQ DIEMHUONG (GETPOINT STPT "Direction from start point:")) (TERPRI) (PROMPT "End point:") (COMMAND "pline" STPT "w" STW ENDW "a" "d" DIEMHUONG PAUSE "") (SETQ STW ENDW) (SETQ ENDPT (CDR (ASSOC 10 (ENTGET (ENTNEXT (ENTNEXT (ENTLAST))))))) (CONGGOP) (SETQ STPT (CAR DSPT1))) ((= ENDPT "So") (TERPRI) (SETQ STPT (GETPOINT STPT "Diem so bo:"))) (T (SETQ VECT nil VEDT nil)))))
(DEFUN VE_PLINE  (/ STPT DSOBO DIEMCUOI SODIEM DS) (SETQ STPT nil STW (GETVAR "plinewid") ENDW STW) (WHILE (/= (TYPE STPT) (QUOTE LIST)) (TERPRI) (INITGET "Diem") (IF DSOBO (SETQ STPT (GETPOINT DSOBO "Diem so bo/<From point>:")) (SETQ STPT (GETPOINT "Diem so bo/<From point>:"))) (COND ((= STPT "Diem") (TERPRI) (INITGET 1) (SETQ DSOBO (GETPOINT "Diem so bo:"))) ((NOT STPT) (TERPRI) (SETQ DT_CHON (ENTSEL "Chon doi tuong muon lay theo:")) (IF DT_CHON (PROGN (SETQ DS (ENTGET (CAR DT_CHON)) LOP_MOI (CDR (ASSOC 8 DS)) MAU_W_NET (CDR (ASSOC 62 DS)) W_NET 0 STW W_NET ENDW STW) (IF MAU_W_NET (SETVAR "cecolor" (SETQ MAU_W_NET (ITOA MAU_W_NET))) (SETVAR "cecolor" "bylayer")) (BAT_LAYER LOP_MOI) (SETVAR "clayer" LOP_MOI) (SETVAR "plinewid" 0) (IF (OR (= (CDR (ASSOC 0 DS)) "POLYLINE") (= (CDR (ASSOC 0 DS)) "LINE")) (PROGN (SETQ SO1 (CDR (ASSOC 71 DS)) SO2 (CDR (ASSOC 72 DS)) SO3 (CDR (ASSOC 73 DS)) W_NET (CDR (ASSOC 40 DS)) LOAI_DUONG (CDR (ASSOC 6 DS))) (IF (NOT W_NET) (SETQ W_NET 0)) (IF (NOT LOAI_DUONG) (SETQ LOAI_DUONG "BYLAYER")) (SETQ STW W_NET ENDW STW) (SETVAR "celtype" LOAI_DUONG)))))) (T nil))) (SETQ VEDT T DSPT1 (LIST STPT) SSENT1 nil) (SETQ STPT (CAR DSPT1)) (WHILE VEDT (TERPRI) (INITGET "Close Arc Undo Width So Loai") (SETQ ENDPT (GETPOINT STPT (STRCAT "diem So bo/Loai duong:" LOAI_DUONG "/Arc/Close/Width/Undo/End point:"))) (COND ((= ENDPT "Arc") (VE_CUNG_TRON)) ((NOT ENDPT) (SETQ VEDT nil)) ((= ENDPT "Width") (NHAP_RONG)) ((= ENDPT "Loai") (CHUYEN_LOAI_DUONG)) ((= ENDPT "Close") (SETQ SODIEM (LENGTH DSPT1) DIEMCUOI (NTH (- SODIEM 1) DSPT1)) (COMMAND "pline" STPT DIEMCUOI "") (CONGGOP) (SETQ VEDT nil)) ((= ENDPT "Undo") (IF (> (LENGTH DSPT1) 1) (PROGN (SETQ SSENT1 (SSDEL (ENTLAST) SSENT1) DSPT1 (CDR DSPT1)) (SETQ STPT (CAR DSPT1)) (ENTDEL (ENTLAST))))) ((= (TYPE ENDPT) (QUOTE LIST)) (SETQ STPT (CAR DSPT1)) (COMMAND "pline" STPT "w" STW ENDW ENDPT "") (SETQ STW ENDW) (CONGGOP) (SETQ STPT (CAR DSPT1))) ((= ENDPT "So") (TERPRI) (SETQ STPT (GETPOINT STPT "Diem so bo:"))) (T (SETQ VEDT nil)))))
(DEFUN XEM_THEO_DIEU_KIEN  (/ TENKT1 SO_LAN TENKT IDE_DOC CD_IDE KY_TU CO_TEP KY_TU_DOC CD MA_SO MA_SO_CHOI F) (SETVAR "cmdecho" 0) (PROGN (SETQ M:ERR *ERROR*) (PRINC)) (DEFUN *ERROR* (MSG) (TERPRI) (PRINC MSG) (TERPRI) (IF (SETQ TF (FINDFILE "tep_id.txt")) (PROGN (SETQ F (OPEN TF "w")) (CLOSE F) (IF (SETQ F (FINDFILE "thuuydd.txt")) (COMMAND "sh" (STRCAT "del " F))) (COMMAND "sh" (STRCAT "ren " TF " thuuydd.txt")) (COMMAND "sh" "del thuuydd.txt"))) (SETVAR "FILEDIA" 0) (COMMAND "quit" "y") (SETQ *ERROR* M:ERR M:ERR nil) (PRINC) (PRINC)) (TEXTSCR) (IF (NOT (FINDFILE "render.exe")) (CHAY_THOAT_CHOI)) (IF (NOT (FINDFILE "acadid.exe")) (CHAY_THOAT_CHOI)) (IF (AND (NOT (FINDFILE "adfor.mbt")) (NOT (FINDFILE "adforf.mbt"))) (CHAY_THOAT_CHOI)) (SETQ CO_TEP nil THOA_MAN_CUOC_CHOI nil THU_HANG nil) (IF (FINDFILE "adfor.mbt") (PROGN (SETQ CACH 1 CO_TEP T) (TD_THEO_CACH1))) (IF (FINDFILE "adforf.mbt") (PROGN (SETQ CACH 2 CO_TEP T) (TD_THEO_CACH2))) (IF (NOT CO_TEP) (CHAY_THOAT_CHOI)) (IF (NOT THOA_MAN_CUOC_CHOI) (CHAY_THOAT_CHOI)) (SETQ CD (STRLEN DONG_NAME) N 0 TEN_NGUOISD "") (IF (< CD 100) (CHAY_THOAT_CHOI)) (WHILE (< N CD) (SETQ KTU (SUBSTR DONG_NAME (+ (* N 5) 1) 1) N (+ N 1)) (IF (/= KTU "@") (SETQ TEN_NGUOISD (STRCAT TEN_NGUOISD KTU)) (SETQ N CD))) (SETQ CD (STRLEN DONG_CQ) N 0 TEN_COQUANSD "") (IF (< CD 100) (CHAY_THOAT_CHOI)) (WHILE (< N CD) (SETQ KTU (SUBSTR DONG_CQ (+ (* N 5) 1) 1) N (+ N 1)) (IF (/= KTU "@") (SETQ TEN_COQUANSD (STRCAT TEN_COQUANSD KTU)) (SETQ N CD))) (GRAPHSCR) (SETQ *ERROR* M:ERR M:ERR nil) (PRINC) (PRINC) (PRINC) (PRINC))
(DEFUN XEN_BVTVIEN  (TEN /) (SETVAR "cmdecho" 0) (PROGN (SETQ M:ERR *ERROR*) (PRINC)) (DEFUN *ERROR* (MSG) (PRINC MSG) (TERPRI) (SETQ *ERROR* M:ERR M:ERR nil) (PRINC) (PRINC)) (IF (NOT GAN_GT) (PROGN (TERPRI) (PROMPT "Can phai load Start truoc.") (EXIT)) (COMMAND "insert" TEN)))
(DEFUN XOA_LAYER  (TEN / SS N CD) (BAT_LAYER TEN) (SETQ N 0 SS (SSGET "X" (LIST (CONS 8 TEN)))) (IF SS (PROGN (SETQ CD (SSLENGTH SS)) (WHILE (< N CD) (SETQ TEN (SSNAME SS N)) (ENTDEL TEN) (SETQ N (+ N 1))))))
(DEFUN XOA_NHOM_DT  (SS / N CD) (IF SS (PROGN (SETQ N 0 CD (SSLENGTH SS)) (WHILE (< N CD) (ENTDEL (SSNAME SS N)) (SETQ N (+ N 1))))))
(DEFUN XUONG_DONG  (F) (PRINC "\n" F))
(load "STARTUP")
(load "ddatools")
