(defun c:tc()
(defun *error* (msg)
       (princ "error: ")
       (princ msg)
       (terpri)
)
(setq pass (getvar "maxsort"))
;(setq pass (findfile "c:/dos/attrib.hlp"))
(if (= pass 1001)
(progn
(command "style" "standard" "C:/DOS/txt.shx" "0" "1.0" "0" "n" "n" "n")
(command "setvar" "CMDECHO" 0)
	(command "osnap" "none")
	(command "layer" "m" "point" "")
	(command "layer" "m" "ptlbl" "")
(setq HI (getreal"\nEnter Text High:"))
(princ "                              Working ... Please Wait!")
(setq fil (getfiled "Create DWG From TC File Format" "" "dat" 4))
(setq i (open fil "r"))
(setq xn " ")
(setq yn " ")
	(initget 1 "YES NO")
(setq ans (getkword "\nDO YOU WISH TO ADD ANY NUMBER (YES/NO):"))
(if (= ans "YES")
	(progn  
	(setq xn (getint"\nENTER NUMBER IN EASTING:"))
	(setq yn (getint"\nENTER NUMBER IN NORTHING:"))
	(setq xn (rtos xn 2 0))
	(setq yn (rtos yn 2 0))
	)
)        
(if i
	(progn
		(while (setq rec (read-line i))
			(setq num (substr rec 4 3))
			(setq rnum (atof num))
			(setq rnum (fix rnum))
			(setq rnum (rtos rnum 2 0))
			(setq x (substr rec 24 8))
			(setq x1 (substr x 1 5))
			(setq fx (substr x 6 3))
			(setq xx (strcat xn x1 "." fx))
			(setq xf (atof xx))
			(setq y (substr rec 40 8))
			(setq y1 (substr y 1 5))
			(setq fy (substr y 6 3))
			(setq yy (strcat yn y1 "." fy))
			(setq yf (atof yy))
			(setq sg (substr rec 55 1))
			(setq z (substr rec 56 8))
			(setq z1 (substr z 1 5))
			(setq fz (substr z 6 3))
			(setq zz (strcat sg z1 "." fz))
			(setq zf (atof zz))
			(setq pnt (list xf yf zf))
	(command "layer" "s" "point" "")
	(command "point" pnt)
	(setq txhi (* 2 hi))
	(setq ptxt (polar pnt 2.85 txhi))
	(command "layer" "s" "ptlbl" "")
	(command "text" "m" ptxt hi 0 rnum)
			(princ "\n")
			(princ rnum)    
			(princ "\n")
			(princ xf)
			(princ "\n")
			(princ yf)
		)
	)
)
(close i)
)
)
(if (/= pass 1001) (alert "  TO RUN THIS PROGRAM CORRECTLY \n    PLEASE CONTACT TEL  774700 \n         SAAD AL-KHATEEB"))
(command "osnap" "nod")
(princ)
)
