;;|------------------------------------------------------------------|
;;| Chuong trinh ve bang thong ke thep hinh                          |
;;| Ngon ngu lap trinh Autolisp chay tren nen Autocad                |
;;| Tac gia         : Ku su Nguyen Phu Binh                          |
;;| Ngay viet       : 06/09/1996				     |
;;| Updated by      : Nguyen Manh Dung 42 XD1 DHXD (01/10/2001)      |
;;| Rat mong nhung ai su dung chuong trinh nay chi sua phan chuong   |
;;| trinh cho thich hop va khong nen sua ten tac gia cua chuong trinh|
;;| . Rat chan thanh cam on . Chuc ban thanh dat trong nghe nghiep.  |
;;| . Luu y : chuong trinh can cac bo dau tieng viet ho roman        |
;;|------------------------------------------------------------------|

;; Phan 1 : Ve tieu de bang thong ke --------------------------------
;; ------------------------------------------------------------------

;; Tieu de thong ke thep tron --------------------
(defun c:tdc ()
(setq pt (getpoint "Diem chen tieu de cua bang :"))
(command "osnap" "off")
(setq xg (car pt))
(setq yg (cadr pt))
(command "setvar" "cmdecho" "0")
(command "style" "Tk" "vnromanc,vns" "4" "1.2" "0" "" "" "")
(command "osnap" "off")
(command "color" "3")
(command "text" "c" (list (+ xg 80) (+ yg 4)) "0" "BA/RNG THO/M/SNG KE/M THE/SP")
(command "line" (list xg yg) (list (+ xg 160) yg)
(list (+ xg 160) (- yg 16)) (list xg (- yg 16)) "c" "")
(command "color" "2")
(command "line" (list (+ xg 20) yg) (list (+ xg 20) (- yg 16)) "")
(command "line" (list (+ xg 30) yg) (list (+ xg 30) (- yg 16)) "")
(command "line" (list (+ xg 70) yg) (list (+ xg 70) (- yg 16)) "")
(command "line" (list (+ xg 85) yg) (list (+ xg 85) (- yg 16)) "")
(command "line" (list (+ xg 105) yg) (list (+ xg 105) (- yg 16)) "")
(command "line" (list (+ xg 123) (- yg 0)) (list (+ xg 123) (- yg 16)) "")
(command "line" (list (+ xg 140) (- yg 8)) (list (+ xg 140) (- yg 16)) "")
(command "line" (list (+ xg 123) (- yg 8)) (list (+ xg 160) (- yg 8)) "")
(command "style" "tkt" "Vnromanc,vns" "2.5" "0.8" "0" "" "" "")
(command "text" "mc" (list (+ xg 10) (- yg 7)) "0" "C.Kie/m/jn")
(command "text" "mc" (list (+ xg 25) (- yg 4)) "0" "SH")
(command "text" "mc" (list (+ xg 25) (- yg 11.5)) "0" "The/sp")
(command "text" "mc" (list (+ xg 50) (- yg 7)) "0" "Hi/fnh Da/jng Thanh")
(command "text" "mc" (list (+ xg 77.5) (- yg 4)) "0" "/D.Ki/snh")
(command "text" "mc" (list (+ xg 77.5) (- yg 11.5)) "0" "(mm)")
(command "text" "mc" (list (+ xg 95) (- yg 4)) "0" "Chie/m/fu Da/fi")
(command "text" "mc" (list (+ xg 95) (- yg 11.5)) "0" "Thanh(mm)")
(command "text" "mc" (list (+ xg 113.5) (- yg 4)) "0" "S.L/]/[/jng")
(command "text" "mc" (list (+ xg 113.5) (- yg 11.5)) "0" "//1 C.kie/m/jn")
(command "text" "mc" (list (+ xg 140) (- yg 4)) "0" "To/m/rng co/m/jng")
(command "text" "mc" (list (+ xg 131) (- yg 11.5)) "0" "C.Da/fi(m)")
(command "text" "mc" (list (+ xg 150) (- yg 11.5)) "0" "K.L/]/[/jng(kg)")
)
;; Tieu de thong ke thep hinh --------------------
(defun c:tdh ()
(setq pt (getpoint "Diem chen tieu de cua bang :"))
(setq xg (car pt))
(setq yg (cadr pt))
(command "setvar" "cmdecho" "0")
(command "style" "td" "romanc,romancvn" "4" "1.2" "0" "" "" "")
(command "color" "3")
(command "text" "c" (list (+ xg 75) (+ yg 4)) "0" "BA/RNG THO/M/SNG KE/M THE/SP")
(command "line" (list xg yg) (list (+ xg 150) yg)
(list (+ xg 150) (- yg 20)) (list xg (- yg 20)) "c" "")
(command "color" "2")
(command "line" (list (+ xg 20) yg) (list (+ xg 20) (- yg 20)) "")
(command "line" (list (+ xg 30) yg) (list (+ xg 30) (- yg 20)) "")
(command "line" (list (+ xg 70) yg) (list (+ xg 70) (- yg 20)) "")
(command "line" (list (+ xg 90) yg) (list (+ xg 90) (- yg 20)) "")
(command "line" (list (+ xg 110) yg) (list (+ xg 110) (- yg 20)) "")
(command "line" (list (+ xg 130) (- yg 10)) (list (+ xg 130) (- yg 20)) "")
(command "line" (list (+ xg 110) (- yg 10)) (list (+ xg 150) (- yg 10)) "")
(command "style" "tkt" "romans,romansvn" "2.5" "0.8" "0" "" "" "")
(command "text" "mc" (list (+ xg 10) (- yg 5)) "0" "Object")
(command "text" "mc" (list (+ xg 25) (- yg 5)) "0" "No")
(command "text" "mc" (list (+ xg 50) (- yg 5)) "0" "Angle bar style")
(command "text" "mc" (list (+ xg 80) (- yg 5)) "0" "Length")
(command "text" "mc" (list (+ xg 80) (- yg 15)) "0" "(mm)")
(command "text" "mc" (list (+ xg 100) (- yg 5)) "0" "Qt")
(command "text" "mc" (list (+ xg 100) (- yg 15)) "0" "//Object")
(command "text" "mc" (list (+ xg 130) (- yg 5)) "0" "Total")
(command "text" "mc" (list (+ xg 120) (- yg 15)) "0" "Length(m)")
(command "text" "mc" (list (+ xg 140) (- yg 15)) "0" "Weight(kg)")
)
;; Tieu de thong ke thep ban ---------------------
(defun c:tdb ()
(setq pt (getpoint "Diem chen tieu de cua bang :"))
(setq xg (car pt))
(setq yg (cadr pt))
(command "setvar" "cmdecho" "0")
(command "style" "td" "romanc,romancvn" "4" "1.2" "0" "" "" "")
(command "color" "3")
(command "text" "c" (list (+ xg 75) (+ yg 4)) "0" "TRUSS STEEL SCHEDULE")
(command "line" (list xg yg) (list (+ xg 150) yg)
(list (+ xg 150) (- yg 20)) (list xg (- yg 20)) "c" "")
(command "color" "2")
(command "line" (list (+ xg 20) yg) (list (+ xg 20) (- yg 20)) "")
(command "line" (list (+ xg 30) yg) (list (+ xg 30) (- yg 20)) "")
(command "line" (list (+ xg 70) yg) (list (+ xg 70) (- yg 20)) "")
(command "line" (list (+ xg 90) yg) (list (+ xg 90) (- yg 20)) "")
(command "line" (list (+ xg 110) yg) (list (+ xg 110) (- yg 20)) "")
(command "line" (list (+ xg 130) (- yg 10)) (list (+ xg 130) (- yg 20)) "")
(command "line" (list (+ xg 110) (- yg 10)) (list (+ xg 150) (- yg 10)) "")
(command "style" "tkt" "romans,romansvn" "2.5" "0.8" "0" "" "" "")
(command "text" "mc" (list (+ xg 10) (- yg 5)) "0" "Object")
(command "text" "mc" (list (+ xg 25) (- yg 5)) "0" "No")
(command "text" "mc" (list (+ xg 50) (- yg 5)) "0" "Section")
(command "text" "mc" (list (+ xg 50) (- yg 15)) "0" "(mm x mm)")
(command "text" "mc" (list (+ xg 80) (- yg 5)) "0" "Thick")
(command "text" "mc" (list (+ xg 80) (- yg 15)) "0" "(mm)")
(command "text" "mc" (list (+ xg 100) (- yg 5)) "0" "Qt")
(command "text" "mc" (list (+ xg 100) (- yg 15)) "0" "//Object")
(command "text" "mc" (list (+ xg 130) (- yg 5)) "0" "Total")
(command "text" "mc" (list (+ xg 120) (- yg 15)) "0" "Area(m2)")
(command "text" "mc" (list (+ xg 140) (- yg 15)) "0" "Weight(kg)")
)

;; Phan 2 : Ve thong ke thep ----------------------------------------
;; ------------------------------------------------------------------

;; Ve thong ke thep tron -----------------------
(defun c:tktc ()
(setq pt (getpoint "Diem chen bang thong ke thep :"))
(setq xg (car pt))
(setq yg (cadr pt))
(command "setvar" "cmdecho" "0")
(setvar "textstyle" "tkt")
(setq tiep "C")
(while (= tiep "C")	 
	(setq caukien (getstring T "Ten cau kien:"))
	(setq sock (getint "So cau kien :"))		
	(setq dem 0)
	(setq hoi "C")
	(while (= hoi "C")
		(setq sh (getstring T "So hieu thep :"))
	  	(command "textscr")
		(setq chon (getint "Hinh dang thep [1-10] 
				   1:Thep gai duong kinh > 10 ----
				   2:Thep tron duong kinh =< 10 ____
				   3:Thep cho cot hinh L 
				   4:Thep dai []
				   5:Thep dam hai dau neo |____|
				   6:Thep moc cau _A_
				   7:Thep bao dai mong hinh bat giac <=>
				   8:Thep vai bo -v-
				   9:Thep dai cot hinh thoi
				   10:Thep dai cot tron
				   11:Thep thang may
				   Chon?: "))
	  	(command "hide")
		(cond 
		((= chon 1) (duong1))
		((= chon 2) (duong2))
		((= chon 3) (duong3))
		((= chon 4) (duong4))
		((= chon 5) (duong5))
		((= chon 6) (duong6))
		((= chon 7) (duong7))
		((= chon 8) (duong8))
		((= chon 9) (duong9))
		((= chon 10) (duong10))
		((= chon 11) (duong11))
		((= chon 12) (duong12))
		((= chon 12) (duong12))
		)
	  	;(if (= chon 1)
		   		
		 ; (while ( < dkct 10)
		  ;     (setq dkct (getreal "Duong kinh cot thep [mm] >=10 :"))		    
		  ;)
		;)
	  	;(if (= chon 2)
		 ;   (while ( >= dkct 10)	
		 ;      (setq dkct (getreal "Duong kinh cot thep [mm] <10 :"))
		 ;   ) 
		;)
	  	;(if (> chon 2) 
		  	(setq dkct (getreal "Duong kinh cot thep [mm] :"))
		;)
		(setq soth (getint "So thanh/1CK :"))
		(command "text" "bl" (list (+ xg 24) (- yg 6)) "0" sh)
		(if (<= dkct 8)
			(command "text" "bl" (list (+ xg 74) (- yg 6)) "0" 
			(strcat "%%c " (rtos dkct 2 0)))
			(command "text" "bl" (list (+ xg 74) (- yg 6)) "0" 
			(strcat "/g " (rtos dkct 2 0)))
		)
		(command "text" "bl" (list (+ xg 90) (- yg 6)) "0" (rtos chieudai 2 0))
		(command "text" "bl" (list (+ xg 112) (- yg 6)) "0" (itoa soth))		
		(setq cdtong (* sock (* soth (/ chieudai 1000))))
		(command "text" "bl" (list (+ xg 126) (- yg 6)) "0" (rtos cdtong 2 2))
		(setq bk (/ dkct 2000))
		(setq khl (* (* (* bk bk) pi) 7850))
		(command "text" "bl" (list (+ xg 145) (- yg 6)) "0" (rtos (* khl cdtong) 2 2))
		(setq yg (- yg 8))
		(setq dem (+ dem 1))
		(initget 1 "C K")
    		(setq hoi (strcase (getkword "Tinh tiep thanh thep khac [C/K] :")))
		(if (= hoi "C")
		(command "line" (list (+ xg 20) yg) (list (+ xg 160) yg) "" "line" (list xg yg) (list  xg (+ yg 8.38)) "" "line" ( list (+ xg 20) yg) (list (+ xg 20) (+ yg 8.38)) "" "line" (list (+ xg 30) yg ) (list (+ xg 30) (+ yg 8.38))"" "line" (list (+ xg 70) yg ) (list (+ xg 70) (+ yg 8.38))"" "line" (list (+ xg 85) yg) (list (+ xg 85) (+ yg 8.38))"""line" (list (+ xg 105) yg ) (list (+ xg 105) (+ yg 8.38))"" "line" (list (+ xg 123) yg) (list (+ xg 123) (+ yg 8.38))"" "line" (list (+ xg 140) yg)(list (+ xg 140) (+ 8.38 yg))"" "line" (list (+ xg 160) yg)(list (+ xg 160) (+ 8.38 yg))"")       
																																																															     
	 	(command "line" (list xg yg) (list (+ xg 160) yg) "" "line" (list xg yg) (list  xg (+ yg 8.38)) "" "line" ( list (+ xg 20) yg) (list (+ xg 20) (+ yg 8.38)) "" "line" (list (+ xg 30) yg ) (list (+ xg 30) (+ yg 8.38))"" "line" (list (+ xg 70) yg ) (list (+ xg 70) (+ yg 8.38))"" "line" (list (+ xg 85) yg) (list (+ xg 85) (+ yg 8.38))"""line" (list (+ xg 105) yg ) (list (+ xg 105) (+ yg 8.38))"" "line" (list (+ xg 123) yg) (list (+ xg 123) (+ yg 8.38))"" "line" (list (+ xg 140) yg)(list (+ xg 140) (+ 8.38 yg))"" "line" (list (+ xg 160) yg)(list (+ xg 160) (+ 8.38 yg))"")        
		
											
		)
	 	)
  			
	(command "text" "c" (list (+ xg 8) (+ yg (* dem 4))) "90" caukien)
	(setq chuoi (strcat "(" (strcat (itoa sock) ")")))
	(command "text" "c" (list (+ xg 16) (+ yg (* dem 4))) "90" chuoi)
	(initget 1 "C K")
	(setq tiep (strcase (getkword "Lam tiep cau kien khac [C/K] :")))
	)
)
;; -------------------------------------------------------------------
(defun duong1 ()
	(setq chieudai (getreal "Chieu dai thanh thep :"))
	(command "color" "3")
	(command "pline" (list (+ xg 39) (- yg 6))
	"w" "0.2" "0.2" (list (+ xg 61) (- yg 6)) "")
	(command "color" "2")
	(command "text" "c" (list (+ xg 50) (- yg 5)) "0" (rtos chieudai 2 0))
)
(defun duong5 ()
	(setq chieux (getreal "Chieu dai phuong X :"))
	(setq chieuy (getreal "Chieu dai phuong Y :"))	
	(setq chieudai (+ chieux (* chieuy 2)))
	(command "color" "3")
	(command "pline" (list (+ xg 39) (- yg 6))
	"w" "0.2" "0.2" (list (+ xg 39) (- yg 2)) 
	(list (+ xg 61) (- yg 2)) (list (+ xg 61) (- yg 6)) "")
	(command "color" "2")
	(command "text" "c" (list (+ xg 50) (- yg 5)) "0" (rtos chieux 2 0))
	(command "text" "br" (list (+ xg 38) (- yg 6)) "0" (rtos chieuy 2 0))
	(command "text" "bl" (list (+ xg 62) (- yg 6)) "0" (rtos chieuy 2 0))
)
(defun duong3 ()
	(setq chieux (getreal "Chieu dai phuong X :"))
	(setq chieuy (getreal "Chieu dai phuong Y :"))	
	(setq chieudai (+ chieux chieuy))
	(command "color" "3")
	(command "pline" (list (+ xg 39) (- yg 6))
	"w" "0.2" "0.2" (list (+ xg 39) (- yg 2)) 
	(list (+ xg 61) (- yg 2)) "")
	(command "color" "2")
	(command "text" "c" (list (+ xg 50) (- yg 5)) "0" (rtos chieux 2 0))
	(command "text" "br" (list (+ xg 38) (- yg 6)) "0" (rtos chieuy 2 0))
)
(defun duong4 ()
	(setq chieux (getreal "Chieu dai phuong X :"))
	(setq chieuy (getreal "Chieu dai phuong Y :"))	
	(setq chieudai (* 2 (+ (+ chieux chieuy) 60)))
	(command "color" "3")
	(command "pline" (list (+ xg 61) (- yg 7))
	"w" "0.2" "0.2" (list (+ xg 61) (- yg 2)) 
	(list (+ xg 39) (- yg 2)) (list (+ xg 39) (- yg 6)) 
	(list (+ xg 64) (- yg 6)) "")
	(command "color" "2")
	(command "text" "c" (list (+ xg 50) (- yg 5)) "0" (rtos chieux 2 0))
	(command "text" "br" (list (+ xg 38) (- yg 6)) "0" (rtos chieuy 2 0))
	(command "text" "bl" (list (+ xg 64) (- yg 6)) "0" (rtos 60 2 0))	
)
(defun duong2 ()
	(setq chieux (getreal "Chieu dai phuong X :"))
	(setq chieudai (+ chieux 100))
	(command "color" "3")
	(command "pline" (list (+ xg 56) (- yg 5))
	"w" "0.2" "0.2" (list (+ xg 61) (- yg 5))
	"a" (list (+ xg 61) (- yg 6)) "l" (list (+ xg 39) (- yg 6))
	"a" (list (+ xg 39) (- yg 5)) "l" (list (+ xg 44) (- yg 5)) "")
	(command "color" "2")
	(command "text" "c" (list (+ xg 50) (- yg 5)) "0" (rtos chieux 2 0))
	(command "text" "c" (list (+ xg 42) (- yg 4)) "0" (rtos 50 2 0))
	(command "text" "c" (list (+ xg 60) (- yg 4)) "0" (rtos 50 2 0))	
)
(defun duong6 ()
	(setq chieudai (getreal "Chieu dai thanh thep :"))
	(command "color" "3")
	(command "pline" (list (+ xg 56) (- yg 5))
	"w" "0.2" "0.2" (list (+ xg 61) (- yg 5))
	"a" (list (+ xg 61) (- yg 6)) "l" (list (+ xg 52) (- yg 6))
	(list (+ xg 52) (- yg 3)) "a" (list (+ xg 48) (- yg 3))
	"l" (list (+ xg 48) (- yg 6)) (list (+ xg 39) (- yg 6))
	"a" (list (+ xg 39) (- yg 5)) "l" (list (+ xg 44) (- yg 5)) "")
	(command "color" "2")
	(command "text" "c" (list (+ xg 60) (- yg 4)) "0" (rtos chieudai 2 0))
)
(defun duong7 ()
	(setq chieux (getreal "Chieu dai phuong X :"))
	(setq chieuy (getreal "Chieu dai phuong Y :"))
  	(setq xien (getreal "Chieu dai doan xien :"))
	(setq chieudai (+(* 2 (+ (+ chieux chieuy) 60)) (* 4 xien)) )
	(command "color" "3")
	(command "pline" (list (+ xg 62) (- yg 5))
	"w" "0.2" "0.2" (list (+ xg 55) (- yg 7)) 
	(list (+ xg 45) (- yg 7)) (list (+ xg 39) (- yg 5)) 
	(list (+ xg 39) (- yg 5)) (list (+ xg 39) (- yg 3)) (list (+ xg 45) (- yg 1)) (list (+ xg 55) (- yg 1))
		 (list (+ xg 61) (- yg 3)) (list (+ xg 61) (- yg 6))"")
	(command "color" "2")
	(command "text" "c" (list (+ xg 50) (- yg 6)) "0" (rtos chieux 2 0))
	(command "text" "br" (list (+ xg 38) (- yg 6)) "0" (rtos chieuy 2 0))
	(command "text" "br" (list (+ xg 45) (- yg 7.5)) "-21" (rtos xien 2 0))
	(command "text" "bl" (list (+ xg 64) (- yg 6)) "0" (rtos 60 2 0))	
)
(defun duong8 ()
	(setq chieuxt (getreal "Chieu dai phuong X tren :"))
  	(setq chieuxd (getreal "Chieu dai phuong X duoi :"))
	(setq xien (getreal "Chieu dai doan xien :"))
	(setq chieudai (+(+ (* chieuxt 2) chieuxd)  (* 2 xien)))
	(command "color" "3")
	(command "pline" (list (+ xg 62) (- yg 1))
	"w" "0.2" "0.2" (list (+ xg 58) (- yg 1)) 
	(list (+ xg 54) (- yg 7)) (list (+ xg 47) (- yg 7)) 
	(list (+ xg 43) (- yg 1)) (list (+ xg 39) (- yg 1)) "")
	(command "color" "2")
	(command "text" "c" (list (+ xg 61) (- yg 5)) "0" (rtos chieuxt 2 0))
	(command "text" "c" (list (+ xg 50.5) (- yg 6)) "0" (rtos chieuxd 2 0))
	(command "text" "br" (list (+ xg 43) (- yg 7.5)) "-50" (rtos xien 2 0))
)
(defun duong9 ()
	(setq chieux (getreal "Chieu dai phuong xien 1 :"))
	(setq chieuy (getreal "Chieu dai phuong xien 2 :"))
	(setq chieudai (* 2(+(+ chieux chieuy) 60))) 
	(command "color" "3")
	(command "pline" (list (+ xg 60) (- yg 3))
	"w" "0.2" "0.2" (list (+ xg 50) (- yg 7.1)) 
	(list (+ xg 42) (- yg 3.7)) 
	(list (+ xg 50) (- yg 1)) (list (+ xg 60) (- yg 4.5)) "")
	(command "color" "2")
	(command "text" "c" (list (+ xg 48.8) (- yg 5.8)) "-33" (rtos chieux 2 0))
	(command "text" "br" (list (+ xg 59.5) (- yg 6.4)) "31" (rtos chieuy 2 0))
	(command "text" "bl" (list (+ xg 62) (- yg 6)) "0" (rtos 60 2 0))	
)
(defun duong10 ()
	(setq duongkinh (getreal "Duong kinh vong dai :"))
  	(setq chieudai (+(*(* 2 3.1416) duongkinh) 120))
  	(setq bk (/ duongkinh 2))
	(command "color" "3")
	(command "donut" "6.5" "6.7"(list (+ xg 50) (- yg 4))"")
	(command "pline" (list(+ xg 53.3) (- yg 4))"w" "0.2" "0.2" (list(+ xg 54.2)(- yg 3))"")
	(command "pline" (list(+ xg 53.3) (- yg 4)) "w" "0.2" "0.2" (list(+ xg 54.2)(- yg 5))"")	 
	(command "color" "2")
  	(command "text" "c" (list (+ xg 38) (- yg 5)) "0" "R")
	(command "text" "c" (list (+ xg 42) (- yg 5)) "0" (rtos bk 2 0))
	(command "text" "c" (list (+ xg 60) (- yg 5)) "0" (rtos 60 2 0))
) 
(defun duong11 ()
	(setq chieux (getreal "Chieu dai phuong X :"))
	(setq chieuy (getreal "Chieu dai phuong Y :"))	
	(setq chieudai (+(* chieux 2) chieuy))
	(command "color" "3")
	(command "pline" (list (+ xg 61) (- yg 2))
	"w" "0.2" "0.2" (list (+ xg 39) (- yg 2)) (list (+ xg 39) (- yg 6)) 
	(list (+ xg 61) (- yg 6)) "")
	(command "color" "2")
	(command "text" "c" (list (+ xg 50) (- yg 5)) "0" (rtos chieux 2 0))
	(command "text" "br" (list (+ xg 38) (- yg 6)) "0" (rtos chieuy 2 0))
)
(defun duong12 ()
	(setq chieudai (getreal "Chieu dai thanh thep :"))
	(command "color" "2")
)
;; Ve thong ke thep hinh -----------------------
(defun c:tkth ()
(setq pt (getpoint "Diem chen bang thong ke thep :"))
(setq xg (car pt))
(setq yg (cadr pt))
(command "setvar" "cmdecho" "0")
(setvar "textstyle" "tkt")
(setq tiep "Y")
(while (= tiep "Y")
	(setq caukien (getstring T "Ten cau kien:"))
	(setq sock (getint "So cau kien :"))		
	(setq dem 0)
	(setq hoi "C")
	(while (= hoi "C")
		(setq sh (getstring T "So hieu thep :"))
		(setq kieu (strcase(getstring T "Kieu thep goc :")))
		(trathep)
		(setq chieudai (getreal "Chieu dai thanh thep [mm]:"))
		(setq soth (getint "So luong cua 1 cau kien :"))
		(command "text" "bl" (list (+ xg 23) (- yg 6)) "0" sh)
		(command "text" "bl" (list (+ xg 40) (- yg 6)) "0" kieu)
		(command "text" "bl" (list (+ xg 75) (- yg 6)) "0" (rtos chieudai 2 0))
		(command "text" "bl" (list (+ xg 98) (- yg 6)) "0" (itoa soth))
		(setq cdtong (* sock (* soth (/ chieudai 1000))))
		(command "text" "bl" (list (+ xg 115) (- yg 6)) "0" (rtos cdtong 2 2))
		(command "text" "bl" (list (+ xg 134) (- yg 6)) "0" (rtos (* kldv cdtong) 2 2))
		(setq yg (- yg 8))
		(setq dem (+ dem 1))
		(initget 1 "C K")
    		(setq hoi (strcase (getkword "Tinh tiep thanh thep khac [C/K] :")))
		(if (= hoi "C")
			(command "line" (list (+ xg 20) yg) (list (+ xg 150) yg) "")
			(command "line" (list xg yg) (list (+ xg 150) yg) "")
		)
	)	
	(command "text" "c" (list (+ xg 8) (+ yg (* dem 4))) "90" caukien)
	(setq chuoi (strcat "( " (strcat (itoa sock) " )")))
	(command "text" "c" (list (+ xg 16) (+ yg (* dem 4))) "90" chuoi)
	(initget 1 "Y N")
	(setq tiep (strcase (getkword "Lam tiep cau kien khac [Y/N] :")))
)
)
;; Phan chuong trinh tra thep hinh -------------
(defun trathep ()
	(cond
	((= kieu "L30X20X3") (setq kldv 1.12))
	((= kieu "L30X20X4") (setq kldv 1.46))
	((= kieu "L35X20X4") (setq kldv 1.62))
	((= kieu "L35X20X5") (setq kldv 1.98))
	((= kieu "L45X30X4") (setq kldv 2.26))
	((= kieu "L45X30X6") (setq kldv 3.28))
	((= kieu "L60X40X5") (setq kldv 3.79))
	((= kieu "L60X40X6") (setq kldv 4.49))						
	((= kieu "L60X40X8") (setq kldv 5.84))
	((= kieu "L75X50X5") (setq kldv 4.80))
	((= kieu "L75X50X6") (setq kldv 5.69))
	((= kieu "L75X50X8") (setq kldv 7.43))
	((= kieu "L80X55X6") (setq kldv 6.16))
	((= kieu "L80X55X8") (setq kldv 8.06))
	((= kieu "L80X55X10") (setq kldv 9.90))
	((= kieu "L90X60X6") (setq kldv 6.90))						
	((= kieu "L90X60X8") (setq kldv 9.08))
	((= kieu "L90X60X10") (setq kldv 11.10))
	((= kieu "L100X75X8") (setq kldv 10.60))
	((= kieu "L100X75X10") (setq kldv 13.10))
	((= kieu "L120X80X8") (setq kldv 12.20))
	((= kieu "L120X80X10") (setq kldv 16.10))
	((= kieu "L130X90X8") (setq kldv 13.50))
	((= kieu "L130X90X10") (setq kldv 16.70))						
	((= kieu "L60X40X5") (setq kldv 3.79))
	((= kieu "L60X40X6") (setq kldv 4.49))
	((= kieu "L60X40X8") (setq kldv 5.84))
	((= kieu "L75X50X5") (setq kldv 4.80))
	((= kieu "L75X50X6") (setq kldv 5.69))
	((= kieu "L75X50X8") (setq kldv 7.43))
	((= kieu "L80X55X6") (setq kldv 6.16))
	((= kieu "L80X55X8") (setq kldv 8.06))						
	((= kieu "L80X55X10") (setq kldv 9.90))
	((= kieu "L90X60X6") (setq kldv 5.90))
	((= kieu "L90X60X8") (setq kldv 9.03))
	((= kieu "L90X60X10") (setq kldv 11.70))
	((= kieu "L100X75X8") (setq kldv 10.60))
	((= kieu "L100X75X10") (setq kldv 13.10))
	((= kieu "L100X75X12") (setq kldv 15.50))
	((= kieu "L120X80X8") (setq kldv 12.20))						
	((= kieu "L120X80X10") (setq kldv 15.10))
	((= kieu "L120X80X12") (setq kldv 17.90))
	((= kieu "L130X90X8") (setq kldv 13.50))
	((= kieu "L130X90X10") (setq kldv 16.70))
	((= kieu "L130X90X12") (setq kldv 19.80))
	((= kieu "L150X100X10") (setq kldv 19.10))
	((= kieu "L150X100X12") (setq kldv 22.60))
	((= kieu "L150X100X14") (setq kldv 26.20))								
	((= kieu "L180X120X12") (setq kldv 27.40))
	((= kieu "L180X120X14") (setq kldv 31.70))
	((= kieu "L180X120X16") (setq kldv 35.90))
	((= kieu "L200X120X12") (setq kldv 29.20))                                                                        
  	((= kieu "L200X120X14") (setq kldv 33.90))
	((= kieu "L200X120X16") (setq kldv 38.40))
	((= kieu "L200X150X12") (setq kldv 32.20))
	((= kieu "L200X150X14") (setq kldv 42.30))						
	((= kieu "L200X150X16") (setq kldv 47.30))
	((= kieu "L25X16X3") (setq kldv 0.91))
	((= kieu "L32X20X3") (setq kldv 1.17))
	((= kieu "L32X20X4") (setq kldv 1.52))
	((= kieu "L40X25X3") (setq kldv 1.48))
	((= kieu "L40X25X4") (setq kldv 1.94))
	((= kieu "L45X28X3") (setq kldv 1.68))
	((= kieu "L45X28X4") (setq kldv 2.20))						
	((= kieu "L50X32X3") (setq kldv 1.90))
	((= kieu "L50X32X4") (setq kldv 2.50))
	((= kieu "L56X36X3,5") (setq kldv 2.48))
	((= kieu "L56X36X4") (setq kldv 2.81))
	((= kieu "L56X36X5") (setq kldv 3.46))
	((= kieu "L63X40X4") (setq kldv 3.17))
	((= kieu "L63X40X5") (setq kldv 3.91))
	((= kieu "L63X40X6") (setq kldv 4.03))						
	((= kieu "L63X40X8") (setq kldv 6.03))
	((= kieu "L70X45X4,5") (setq kldv 3.98))
	((= kieu "L70X45X5") (setq kldv 4.39))
	((= kieu "L80X50X5") (setq kldv 4.99))
	((= kieu "L80X50X6") (setq kldv 5.92))
	((= kieu "L90X56X5,5") (setq kldv 6.17))
	((= kieu "L90X56X6") (setq kldv 6.70))
	((= kieu "L100X63X6") (setq kldv 7.50))						
	((= kieu "L100X63X7") (setq kldv 8.70))
	((= kieu "L90X56X8") (setq kldv 8.77))
	((= kieu "L100X63X8") (setq kldv 9.90))
	((= kieu "L100X63X10") (setq kldv 12.10))
	((= kieu "L110X70X6,5") (setq kldv 8.99))
	((= kieu "L110X70X7") (setq kldv 9.64))
	((= kieu "L110X70X8") (setq kldv 10.90))
	((= kieu "L125X80X7") (setq kldv 11.04))						
	((= kieu "L125X80X8") (setq kldv 12.53))
	((= kieu "L125X80X10") (setq kldv 15.50))
	((= kieu "L125X80X12") (setq kldv 18.34))
	((= kieu "L140X90X8") (setq kldv 14.13))
	((= kieu "L140X90X10") (setq kldv 17.46))
	((= kieu "L160X100X9") (setq kldv 18.00))
	((= kieu "L160X100X10") (setq kldv 19.85))	
	((= kieu "L160X100X12") (setq kldv 23.60))									
	((= kieu "L160X100X14") (setq kldv 27.30))
	((= kieu "L180X110X10") (setq kldv 22.20))
	((= kieu "L180X110X12") (setq kldv 26.40))						
	((= kieu "L200X125X11") (setq kldv 27.40))
	((= kieu "L200X125X12") (setq kldv 29.70))
	((= kieu "L200X125X14") (setq kldv 34.40))
	((= kieu "L250X160X12") (setq kldv 37.90))
	((= kieu "L250X160X16") (setq kldv 49.90))
	((= kieu "L250X160X18") (setq kldv 55.80))
	((= kieu "L250X160X20") (setq kldv 61.70))
	((= kieu "L63X63X4") (setq kldv 3.90))						
	((= kieu "L63X63X5") (setq kldv 4.82))
	((= kieu "L63X63X6") (setq kldv 5.72))
	((= kieu "L70X70X5") (setq kldv 5.38))
	((= kieu "L70X70X6") (setq kldv 6.40))
	((= kieu "L70X70X7") (setq kldv 7.39))
	((= kieu "L75X75X5") (setq kldv 5.80))
	((= kieu "L75X75X6") (setq kldv 6.89))
	((= kieu "L75X75X7") (setq kldv 7.96))						
	((= kieu "L80X80X5,5") (setq kldv 6.78))
	((= kieu "L80X80X6") (setq kldv 7.36))
	((= kieu "L80X80X7") (setq kldv 8.51))
	((= kieu "L90X90X6") (setq kldv 8.33))
	((= kieu "L90X90X7") (setq kldv 9.64))
	((= kieu "L90X90X8") (setq kldv 10.93))
	((= kieu "L100X100X7") (setq kldv 10.79))
	((= kieu "L100X100X8") (setq kldv 12.25))						
	((= kieu "L100X100X10") (setq kldv 15.10))
	((= kieu "L110X110X7") (setq kldv 11.89))
	((= kieu "L110X110X8") (setq kldv 13.50))
	((= kieu "L125X125X8") (setq kldv 15.50))
	((= kieu "L125X125X10") (setq kldv 19.10))
	((= kieu "L125X125X12") (setq kldv 22.70))
	((= kieu "L140X140X9") (setq kldv 19.40))
	((= kieu "L140X140X10") (setq kldv 21.50))						
	((= kieu "L140X140X12") (setq kldv 25.50))
	((= kieu "L160X160X10") (setq kldv 24.70))
	((= kieu "L160X160X12") (setq kldv 29.40))
	((= kieu "L180X180X11") (setq kldv 30.50))
	((= kieu "L180X180X12") (setq kldv 33.10))
	((= kieu "L200X200X12") (setq kldv 37.00))
	((= kieu "L200X200X14") (setq kldv 42.60))	
	((= kieu "L60X60X5") (setq kldv 4.57))									
	((= kieu "L60X60X6") (setq kldv 5.42))
	((= kieu "L60X60X8") (setq kldv 7.09))
	((= kieu "L65X65X6") (setq kldv 5.93))
	((= kieu "L65X65X8") (setq kldv 7.75))
	((= kieu "L65X65X10") (setq kldv 9.51))						
	((= kieu "L75X75X6") (setq kldv 6.89))
	((= kieu "L75X75X8") (setq kldv 9.03))
	((= kieu "L75X75X10") (setq kldv 11.10))
	((= kieu "L80X80X6") (setq kldv 7.36))
	((= kieu "L80X80X8") (setq kldv 9.66))
	((= kieu "L80X80X10") (setq kldv 11.90))
	((= kieu "L90X90X8") (setq kldv 11.00))
	((= kieu "L90X90X10") (setq kldv 13.50))						
	((= kieu "L90X90X12") (setq kldv 16.00))
	((= kieu "L100X100X8") (setq kldv 12.30))
	((= kieu "L100X100X10") (setq kldv 15.10))
	((= kieu "L100X100X12") (setq kldv 17.90))
	((= kieu "L100X100X14") (setq kldv 20.60))
	((= kieu "L120X120X10") (setq kldv 18.30))
	((= kieu "L120X120X12") (setq kldv 21.10))	
	((= kieu "L120X120X14") (setq kldv 25.10))									
	((= kieu "L120X120X16") (setq kldv 28.40))
	((= kieu "L130X130X10") (setq kldv 20.80))
	((= kieu "L130X130X12") (setq kldv 23.60))
	((= kieu "L130X130X14") (setq kldv 27.30))
	((= kieu "L150X150X12") (setq kldv 27.40))						
	((= kieu "L150X150X14") (setq kldv 31.70))
	((= kieu "L150X150X16") (setq kldv 36.00))
	((= kieu "L180X180X14") (setq kldv 38.30))
	((= kieu "L180X180X18") (setq kldv 43.50))
	((= kieu "L200X200X16") (setq kldv 48.70))
	((= kieu "L200X200X18") (setq kldv 54.40))
	((= kieu "L40X40X4") (setq kldv 2.42))
	((= kieu "L40X40X5") (setq kldv 2.97))						
	((= kieu "L40X40X6") (setq kldv 3.54))
	((= kieu "L45X45X4") (setq kldv 2.73))
	((= kieu "L45X45X5") (setq kldv 3.37))
	((= kieu "L45X45X6") (setq kldv 3.99))
	((= kieu "L50X50X5") (setq kldv 3.77))
	((= kieu "L50X50X6") (setq kldv 4.47))				
	( kieu (nhap))
	)
)
;; ---------------------------------------------
(defun nhap ()
	(setq kldv (getreal "Thep nay chua co , Ban Cho kldv thanh thep :"))
)
;; Ve thong ke thep ban ------------------------
(defun c:tktb ()
(setq pt (getpoint "Diem chen bang thong ke thep :"))
(setq xg (car pt))
(setq yg (cadr pt))
(command "setvar" "cmdecho" "0")
(setvar "textstyle" "tkt")
(setq tiep "Y")
(while (= tiep "Y")
	(setq caukien (getstring T "Ten cau kien:"))
	(setq sock (getint "So cau kien :"))		
	(setq dem 0)
	(setq hoi "C")
	(while (= hoi "C")
		(setq sh (getstring T "So hieu ban thep :"))
		(setq chieurong (getreal "Chieu rong ban thep [mm]:"))
		(setq chieudai (getreal "Chieu dai ban thep [mm]:"))
		(setq k1 (strcat "- "(rtos chieurong 2 0)))
		(setq k2 (strcat "x" (rtos chieudai 2 0)))
		(setq kieu (strcat k1 k2))
		(setq chieuday (getreal "Chieu day ban [mm]:"))
		(setq soth (getint "So luong cua 1 cau kien :"))
		(command "text" "bl" (list (+ xg 23) (- yg 6)) "0" sh)
		(command "text" "bl" (list (+ xg 40) (- yg 6)) "0" kieu)
		(command "text" "bl" (list (+ xg 75) (- yg 6)) "0" (rtos chieuday 2 0))
		(command "text" "bl" (list (+ xg 98) (- yg 6)) "0" (itoa soth))
		(setq dttong (* sock (* soth (/ (* chieurong chieudai) 1000000))))
		(command "text" "bl" (list (+ xg 115) (- yg 6)) "0" (rtos dttong 2 2))
		(command "text" "bl" (list (+ xg 134) (- yg 6)) "0" (rtos (* 7.85 (* chieuday dttong)) 2 2))
		(setq yg (- yg 8))
		(setq dem (+ dem 1))
		(initget 1 "C K")
    		(setq hoi (strcase (getkword "Tinh tiep ban thep khac [C/K] :")))
		(if (= hoi "C")
			(command "line" (list (+ xg 20) yg) (list (+ xg 150) yg) "")
			(command "line" (list xg yg) (list (+ xg 150) yg) "")
		)
	)	
	(command "text" "c" (list (+ xg 8) (+ yg (* dem 4))) "90" caukien)
	(setq chuoi (strcat "( " (strcat (itoa sock) " )")))
	(command "text" "c" (list (+ xg 16) (+ yg (* dem 4))) "90" chuoi)
	(initget 1 "Y N")
	(setq tiep (strcase (getkword "Lam tiep cau kien khac [Y/N] :")))
)
)
;; End of program Rebar Schedule ------------------------------------
;; ------------------------------------------------------------------
