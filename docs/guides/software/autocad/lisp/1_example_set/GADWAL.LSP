(defun C:GAD()
(COMMAND "LAYER" "THAW" "AREA" "")
(COMMAND "LAYER" "SET" "AREA" "")
(command "color" 6)
(setq par (getint"\n Number Of Parcels Please:"))
(setq pt1 (getpoint"\nlower left corner"))
(setq pt3 (getpoint"\nupper right corner"))
(setq pt2 (list (nth 0 pt3) (nth 1 pt1)))
(setq pt4 (list (nth 0 pt1) (nth 1 pt3)))
(command "line" pt1 pt2 pt3 pt4 "c")
(setq d1 (distance pt4 pt1))
(setq d2 (distance pt4 pt3))
(setq ang1 (angle pt4 pt1))
(setq ang2 (angle pt4 pt3))
(setq sdt (/ (1+ par) 2))
(setq sdt (fix sdt))
(setq sd (/ d1 sdt))
(setq tsd (/ d2 6))
(setq cnt 1)
(setq fd 0)
	(while (< cnt sdt)
		(setq fd (+ fd sd))
		(setq ptn (polar pt4 ang1 fd))
		(setq ssg (ssget "w" pt4 pt3))
		(command "copy" ssg "" pt4 ptn)
		(setq cnt (1+ cnt))
	)
(setq cnt2 1)
(setq fdh 0)
	(while (< cnt2 5)
		(if (= cnt2 2) (setq cnt2 (1+ cnt2)))
			(setq fdh (* cnt2 tsd))
			(setq pth (polar pt4 ang2 fdh))
			(setq ssg2 (ssget "w" pt4 pt1))
			(command "copy" ssg2 "" pt4 pth)
			(setq cnt2 (1+ cnt2))
	)
	(setq h1 (/ sd 2))
	(setq h2 (/ tsd 2))
	(setq cnt 1)
	(command "color" 4)
        (while (<= cnt sdt)
		(setq ptxt (polar pt4 ang1 h1))
		(setq ptxt (polar ptxt ang2 h2))
		(setq h1 (+ h1 sd))
		(command "text" "m" ptxt 7 0 cnt)
		(setq cnt (1+ cnt))
	)
	(setq h1 (/ tsd 2))
	(setq h1 (+ (* 3 tsd) h1))
	(setq h2 (/ sd 2))
        (while (<= cnt par)
		(setq ptxt (polar pt4 ang2 h1))
		(setq ptxt (polar ptxt ang1 h2))
		(setq h2 (+ h2 sd))
		(command "text" "m" ptxt 7 0 cnt)
		(setq cnt (1+ cnt))
	)
	(command "color" 6)
	(setq txt1 "PAR#")
	(setq txt2 "AREA")
	(setq ang3 (+ pi ang1))
	(setq pnt (polar pt4 ang3 sd))
	(command "line" pt4 pnt "")
	(command "copy" ssg "" pt4 pnt)
	(setq pnt (polar pt3 ang3 sd))
	(command "line" pt3 pnt "")
	(setq pnt (polar pt4 ang2 tsd))
	(setq pnt1 (polar pnt ang3 sd))
	(command "line" pnt1 pnt "")
	(setq h1 (* 3 tsd))
	(setq pnt (polar pt4 ang2 h1))
	(setq pnt1 (polar pnt ang3 sd))
	(command "line" pnt1 pnt "")
	(setq h1 (* 4 tsd))
	(setq pnt (polar pt4 ang2 h1))
	(setq pnt1 (polar pnt ang3 sd))
	(command "line" pnt1 pnt "")
	(setq pnt (polar pt4 ang2 tsd))
	(command "text" "a" pt4 pnt txt1)
	(setq sdn (* 3 tsd))
	(setq sdn1 (* 4 tsd))
	(setq pnt1 (polar pt4 ang2 sdn))
	(command "text" "a" pnt pnt1 txt2)
	(setq pnt2 (polar pt4 ang2 sdn1))
	(command "text" "a" pnt1 pnt2 txt1)
	(command "text" "a" pnt2 pt3 txt2)
)
