(prompt "Please wait PCO.LSP is loading .... ")
(DEFUN C:GBL() (COMMAND "INSERT" "*C:/SETHU/GBL" "END" PAUSE "" "" "")(PRINC))
(DEFUN C:GBR() (COMMAND "INSERT" "*C:/SETHU/GBR" "END" PAUSE "" "" "")(PRINC))
(DEFUN C:GTL() (COMMAND "INSERT" "*C:/SETHU/GTL" "END" PAUSE "" "" "")(PRINC))
(DEFUN C:GTR() (COMMAND "INSERT" "*C:/SETHU/GTR" "END" PAUSE "" "" "")(PRINC))
(DEFUN C:HT()(COMMAND "HATCH" "U" "ENDP" PAUSE "ENDP" PAUSE "1" "N")(PRINC))
(DEFUN C:LL()(COMMAND "INSERT" "L" "INT" PAUSE "" "" "NEA")(PRINC))
(DEFUN C:E0()
(SETQ E0SEL(SSGET))
(COMMAND "CHANGE" E0SEL "" "P" "E" "0" "")(PRINC))
(defun c:tmp()(command "insert" "temple" pause "" "" "")(princ))
(defun c:msk()(command "insert" "mosque" pause "" "" "")(princ))
(defun c:chr()(command "insert" "church" pause "" "" "")(princ))
(DEFUN C:W0()(COMMAND "PEDIT" PAUSE "W" "0" "")(PRINC))
(DEFUN C:W1()(COMMAND "PEDIT" PAUSE "W" ".1" "")(PRINC))
(DEFUN C:W2()(COMMAND "PEDIT" PAUSE "W" ".2" "")(PRINC))
(DEFUN C:W5()(COMMAND "PEDIT" PAUSE "W" ".5" "")(PRINC))
(DEFUN C:W4()(COMMAND "PEDIT" PAUSE "W" ".4" "")(PRINC))
(DEFUN C:AE()(COMMAND "AREA" "E")(PRINC))
(DEFUN C:MTS()(COMMAND "CHANGE" PAUSE "" "" "" "" "" "" "METRES")(PRINC))
(DEFUN C:CMD()
	(COMMAND "COPY" PAUSE "" "@" "@4<270")
	(COMMAND "CHANGE" "L" "" "" "" "" "" "METRES")(PRINC))
(DEFUN C:CML()
	(COMMAND "COPY" PAUSE "" "@" "@4<0")
	(COMMAND "CHANGE" "L" "" "" "" "" "" "METRES")(PRINC))
(DEFUN C:CM()(SETQ SEL(SSGET))
(COMMAND "COPY" SEL "" "M")(PRINC))
(DEFUN C:SN()
	(SETVAR "ORTHOMODE" 0)
	(COMMAND "SNAPANG" PAUSE PAUSE)
	(SETVAR "ORTHOMODE" 1)
	(COMMAND "PLINE")(PRINC))
(DEFUN C:s3()
	(SETVAR "ORTHOMODE" 0)
	(COMMAND "SNAPANG" PAUSE PAUSE)
	(SETVAR "ORTHOMODE" 1)
	(COMMAND "3dPoly")(PRINC))
(DEFUN C:0()
	(SETVAR "SNAPANG" 0)
	(SETVAR "ORTHOMODE" 0)(PRINC))
(defun c:wat()
	  (setq a(ssget))
		(command "chprop" a "" "la" "WATER" "")
	(princ)
)
(defun c:sp()
	  (command "insert" "sp" pause "" "" "")
	 (princ)
)
(defun c:Tp()
	  (command "insert" "Tp" pause "" "" "")
	 (princ)
)
(defun c:EpP()
	  (command "insert" "Ep" pause "" "" "")
	 (princ)
)
(defun c:tre()
	(command "chprop" pause "" "la" "tree" "" )
	(princ)
)
(defun c:TMPL()
	  (command "insert" "TEMPLE" pause "" "" "")
	 (princ)
)
(defun c:MSQ()
	  (command "insert" "MOSQUE" pause "" "" "")
	 (princ)
)
(defun c:CRCH()
	  (command "insert" "CHURCH" pause "" "" "")
	 (princ)
)
(defun c:rsp()
(setq la(getvar "clayer"))
(setvar "clayer" "sp-ht")
(setq po(getpoint "\nPick SP point: "))
(setq txt(getstring "\nEnter value: "))
(command "insert" "sp" po "" "" "")
  (command "text" "s" "rs2" "@1<0" "0" txt)
(setvar "clayer" la) 
(command "move" "la" "")(princ))
(defun c:BRG()
	  (command "insert" "BRG" pause "" "")
	 (princ)
)
(DEFUN C:HGR()
	(COMMAND "INSERT" "HGR" PAUSE "" "")
	(PRINC)
)
(DEFUN C:ARW()
	(COMMAND "INSERT" "AR" PAUSE "" "")(PRINC))
(DEFUN C:ARL()
(SETVAR "CLAYER" "TEXT")
(SETVAR "DIMASZ" 2)
(COMMAND "DIM" "L" PAUSE PAUSE ^C "E")
(COMMAND "PEDIT" "L" "Y" "W" "0.2" "X")
(COMMAND "CHPROP" "L" "" "LT" "DASHED" "")
(PRINC))
(DEFUN C:ARs()
	(COMMAND "INSERT" "ARs" PAUSE "" "")(PRINC))
(DEFUN C:AR1()
(COMMAND "INSERT" "AR1" "NEA"  PAUSE "" "" "NEA" PAUSE)
(PRINC)
)
(DEFUN C:AR2()
(COMMAND "INSERT" "AR2" "NEA"  PAUSE "" "" "NEA" PAUSE)
(PRINC)
)
(DEFUN C:GATE()
	(COMMAND "INSERT" "GATE" PAUSE "" "")(PRINC))
(DEFUN C:MT()(COMMAND "MEASURE" PAUSE "B" "CUT" "Y")(PRINC))
(DEFUN C:MT1()(COMMAND "MEASURE" PAUSE "B" "CUT1" "Y")(PRINC))
(DEFUN C:MF()(COMMAND "MEASURE" PAUSE "B" "FEN" "Y")(PRINC))
(DEFUN C:SCA()(COMMAND "SCALE" "ALL" "" "0,0")(PRINC))
(DEFUN C:CTR()(COMMAND "INSERT" "CTR" PAUSE "" "" "")(PRINC))
(defun c:PH()
	  (command "insert" "PH" pause "" "" "")
	 (princ)
)
(DEFUN C:PLI()
	(COMMAND "OSNAP" "NEA")
	(COMMAND "INSERT" "PL" PAUSE "" "" PAUSE)
	(COMMAND "OSNAP" "")
	(PRINC)
)
(defun c:tree()
	  (command "insert" "tr" pause "" "" "")
	 (princ)
)
(defun c:ref()
	  (command "insert" "ref" pause "" "" "")
	 (princ)
)
(defun c:rs()
	  (command "dtext" "s" "rs" "m")
	 (princ)
)
(defun c:rs4()
	  (command "dtext" "s" "rs4" "m")
	 (princ)
)
(defun c:IC()
	  (command "dtext" "s" "IC" "m" PAUSE "0")
	 (princ)
)
(DEFUN C:RS1()(COMMAND "DTEXT" "s" "RS1" "m" pause "0")(PRINC))
(DEFUN C:RS2()(COMMAND "DTEXT" "s" "RS2" "m" pause "0")(PRINC))
(DEFUN C:RS25()(COMMAND "DTEXT" "s" "RS25" "m" pause "PER")(PRINC))
(defun c:RSA()
	(command "dtext" "s" "rsc" "nea" pause "nea" pause)
	(command "move" "l" "" "@" pause)
	(command "break" pause pause)
	(command "chprop" pause "" "la" "con-txt" "")
  (princ)
)
(defun c:rsc()
	  (command "dtext" "s" "rsc" "M")
	 (princ)
) 
(defun c:is()
	  (command "dtext" "s" "is" "m")
	 (princ)
)
(defun c:rc()
	  (command "dtext" "s" "rc" "m")
	 (princ)
)
(defun c:srd()
	  (command "dtext" "s" "rd" "mc")
	 (princ)
)
(defun c:rd()
	(setq a(ssget))
	 (command "chprop" a "" "la" "road" "")
	(princ)
)
(defun c:trs()
	 (setq a(ssget))
	 (command "chprop" a "" "la" "tree" "")
	(princ)
)

(DEFUN C:Pw() (SETQ A(SSGET)) (COMMAND "CHPROP" A "" "LA" "POWER" "") (PRINC))
(DEFUN C:TC()(COMMAND "TABLET" "CAL")(PRINC))
;(DEFUN C:HA()(COMMAND "HATCH" "U" "45" "1" "N")(PRINC))
(defun c:ha()
(setq sn(getvar "snapang"))
(setq fc(+ (* sn (/ 180 pi)) 45))
(setq sel1(SSGET))
(command "hatch" "u" fc "1" "n" sel1 "")
  (princ))
(DEFUN C:H8()(COMMAND "HATCH" "U" "NEA" PAUSE "NEA" PAUSE "1.8" "N")(PRINC))
(DEFUN C:H2()
	(COMMAND "OFFSET" "2" PAUSE PAUSE "")
	(COMMAND "HATCH" "U" "ENDP" PAUSE "ENDP" PAUSE "1" "N")
	(PRINC))
(DEFUN C:LN()
	 (SETQ A(GETSTRING "\nLAYER NAME(S) TO TURN ON :"))
	 (COMMAND "LAYER" "ON" A "")
	(princ)
)
(DEFUN C:LF()
	 (SETQ A(GETSTRING "\nLAYER NAME(S) TO TURN OFF :"))
	 (COMMAND "LAYER" "OFF" A "")
	(princ)
)
(defun c:WA()
	  (prompt "text insertion point")
	  (command "text" "s" "rs" pause "0" "W")
	  (command "chprop" "l" "" "la" "txt" "")(princ)
)
(DEFUN C:PLA()(COMMAND "PLINE" PAUSE "A" "s")(PRINC))
(defun c:L1()
	  (command "insert" "L1" "END" pause "" "" "")
	 (princ))

(DEFUN C:II()
	(setq NAME_(getstring "\nPlease give me block name: "))
(command "insert" NAME_ pause "" "" "")(princ))
(DEFUN C:CRS1()
(COMMAND "CHANGE" PAUSE "" "" "" "RS1" "" "")(PRINC))
(DEFUN C:CRS()(COMMAND "CHANGE" PAUSE "" "" "" "RS" "" "")
(COMMAND "MOVE" "P" "" "@")(PRINC))
(DEFUN C:CRS2()
(COMMAND "CHANGE" PAUSE "" "" "" "RS2" "0" "")
(COMMAND "MOVE" "P" "" "@")(PRINC))
(DEFUN C:CRSC()(COMMAND "CHANGE" PAUSE "" "" "" "RSC" "" "")(PRINC))
(DEFUN C:CIS ()
  (setq sset2 (car (ENTsel "\nSelect text to change to IS style: ")))
  (setq sset1 (entget sset2))
  (setq oldS (assoc 7 sset1))
  (setq newS (cons 7 "IS"))
  (setq entch (subst newS oldS sset1))
  (setq old (assoc 51 entch))
  (setq new (cons 51 (* (/ pi 180) 15)))
  (setq emod (subst new old entch))
  (entmod emod)
  (princ)
)
(DEFUN C:T0()
	(COMMAND "CHANGE" PAUSE "" "" "" "" "0" "")
	(COMMAND "MOVE" "P" "" "@")(PRINC))
(defun c:tx0()
(command "change" pause "" "" "" "" "0" "")
(command "move" "p" "" "@" ".x" "ins" pause)(princ))
(DEFUN C:MT0()
	(COMMAND "CHANGE" PAUSE "" "" "" "" "0" "")
	(COMMAND "MOVE" "P" "" "@" PAUSE)
	(C:MT0)(PRINC))
(DEFUN C:VE()(COMMAND "VIEW" "r" "e")(PRINC))
(DEFUN C:VS()(COMMAND "VIEW" "s")(PRINC))
(DEFUN C:VR()(COMMAND "VIEW" "r")(PRINC))
(defun c:vw()(command "view" "w")(princ))
(defun c:cls()(grclear))
(DEFUN C:FR()
	(SETQ RADIUS(GETSTRING "\nENTER FILLET RADIUS: "))
	(COMMAND "FILLET" "R" RADIUS)
	(COMMAND "FILLET")(PRINC))
(DEFUN C:STM()
(COMMAND "MENU" "C:/AUTOCVL7/ST")(PRINC))
(DEFUN C:FRR()
 (COMMAND "FILLET" "R")(PRINC))
(DEFUN C:FC()
 (COMMAND "FILLET" "C")(PRINC))
(DEFUN C:ATT()
	(COMMAND "ATTEDIT" "Y" "" "" "" PAUSE "" "P" PAUSE "")
	(PRINC)
)
(DEFUN C:AT1()
	(COMMAND "ATTEDIT" "Y" "" "" "" PAUSE "" "a" "0" "p" pause "LA" "NEW-CVD-PTEL" "")
	(PRINC)
)
(defun c:xr()
(command "xref" "a" "~" "0,0" "" "" "")(princ))
(defun c:xs()
(command "xref" "a" "~" "0,0" "0.4" "" "")(princ))
(defun c:xd()
(command "xref" "d" "*")(princ))
(defun c:bold()
(SETVAR "REGENMODE" 0)
(command "style" "b" "bold" "4" "" "" "" "")
(COMMAND "style" "monotxt" "romans" "" "" "" "" "" "")
(command "layer" "s" "0" "c" "20" "boundary,bou" 
"C" "15" "CVD-HVYL" "C" "1" "CUTTING,FENCE,cvd-cant" "f" "cvd-ptxt" "")
(SETVAR "REGENMODE" 1)(princ))
;(DEFUN C:LM()
;(LOAD "C:/ACAD12/SUPPORT/MANGLA.LSP")(PRINC))
;(DEFUN C:Mla()
;(LOAD "C:/ACAD12/SUPPORT/LA.LSP")(PRINC))
(DEFUN C:MXd()
(SETQ PS(GETPOINT "\nGET SECOND POINT: "))
(COMMAND "ZOOM" "E")
(command "zoom" "0.9x")
(command "chprop" "l" "" "la" "0" "c" "bylayer" "")
(COMMAND "ZOOM" "W" pause pause)
(c:mx1)
(PRINC))
(defun c:3B()
	(SETVAR "ORTHOMODE" 0)
	(COMMAND "SNAPANG" PAUSE PAUSE)
	(SETVAR "ORTHOMODE" 1)
(c:bp1)(princ))
(DEFUN C:bp1()
(setvar "osmode" 8)
(SETQ PT(GETPOINT "\nFrom point: "))
(setq pt2(getpoint pt "\nPick point: "))
(setq pt1(list (car pt) (cadr pt) (caddr pt2)))
(command "3dpoly" pt1 pt2)(princ))
(defun c:led()
(command "dim" "leader" pause pause ^c "e")(princ))
(DEFUN C:MX1()
(SETQ SEL(ssget))
(SETQ PB(GETPOINT "\nPick Base point: "))
(SETQ PSS(LIST (CAR PS) (+ (CADR PS) 40)))
(COMMAND "MOVE" SEL "" pb pss)(princ))
(defun c:cs()
(setq sel(ssget))
(command "chprop" sel "" "la" "cs-pnts" "")(princ))
(defun c:s5()
  (setvar "regenmode" 1)
  (setq basept(getvar "insbase"))
  (command "scale" "all" "" basept "0.5")(princ))
(Prompt "Thank you > PCO.LSP Loaded. ")
