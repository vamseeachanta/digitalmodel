(defun c:ACRE (/ )
        (setq pentity (car(entsel "\nPick polyline for area: ")))
        (command "area" "e" pentity)
        (setq area1 (getvar "area"))
        (setq acreage (/ area1 43560.0))
        (setq acre (rtos acreage 2 4))
        (setq art (strcat " = " acre " Acres" (chr 13)))
        (setq sqrft (strcat "Area = " (rtos area1 2 0) " SqFt"))
        (setq art_sqrft (strcat sqrft art))
        (PROMPT art_sqrft)
)
