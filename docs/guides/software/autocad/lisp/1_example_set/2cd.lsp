(defun c:cd(/ pt1 pt2 east north)
(setvar "cmdecho" 0)
(setq pt1 (getpoint "\nPick point :"))
(setq pt2 (getpoint pt1 "\nPick Text location :"))
 (setq east  (strcat "E=" (rtos (car  pt1) 2 4)))
 (setq north (strcat "N=" (rtos (cadr pt1) 2 4)))
 (command "leader" pt1 pt2 "a" east  north "")
 (princ)
)
