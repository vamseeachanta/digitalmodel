;;;(defun c:ER ()
;;;  (princ "\nErase recently created entity")
;;;  (command "erase" "L" "")
;;;  (princ)
;;;)
(defun c:o (/ od ob s)
  (command "undo" "begin")
  (SETVAR "CMDECHO" 0)
 (setq *os (getvar "osmode"))
  (princ (strcat "\nOffset distance or Through <" (rtos (getvar "offsetdist")) ">:"))
 (setq od (getreal))
  (if (not od) (setq od (getvar "offsetdist")))
 (setvar "osmode" 0)
 (setq ob (entsel "\nSelect object to offset:")
       s (getpoint "\nSide to offset?"))
  (command "offset" od ob s "")
  (setvar "osmode" *os)
  (command "undo" "end")
(princ))
(DEFUN C:SS ()
  (SETVAR "CMDECHO" 0)
  (PRINC)
  (PRINC "STRETCH CROSSING POLY")
  (COMMAND "STRETCH" "Cp")
  (PRINC))
(DEFUN C:MI_SP (/ ss1)
  (SETVAR "CMDECHO" 0)
  (PRINC)
  (PRINC "Mirror Turning Ortho and Midp osnap on")
  (setq ss1 (ssget))
  (setq *om (getvar "orthomode"))
  (setvar "orthomode" 1)
  (COMMAND "Mirror" ss1 "" "midp" pause pause)
  (setvar "orthomode" *om)
  (PRINC))
(defun c:um ()
  (SETVAR
