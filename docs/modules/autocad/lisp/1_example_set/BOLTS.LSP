;=================================================
;Various Bolt Utilities by Andrew NIELSEN
;Elevation of Bolts
;=================================================
(defun BL ()
    (command "LINETYPE" "S" "BYLAYER" "")
    (command "COLOR" "BYLAYER")
)
;=================================================
(defun DTR (angg)
  (* pi (/ angg 180.0)))
;=================================================
(defun C:ELEVBOLT(/ IP1 IP2 D H HD LEN E K R1 S P1 P2 P3 P4 P5
 P6 P7 P8 P9 P10 P11 P12 P13 P14 P15 P16 P17 P18 P19 P20 P21
 P22 P23 P24 P25 P26 RP1 D1 D2)
  (command ".UNDO" "M")
  (setq BLM (getvar "BLIPMODE")
        OSM (getvar "OSMODE"))
  (setvar "OSMODE" 32)
  (bl)
  (initget 1 "H S B")
  (setq HD(strcase(getkword "\nHex Socket or Button Head?  H,S,B ")))
  (setq IP1 (getpoint "\nPick insertion point of bolt ...O/S=int>"))
  (setvar "OSMODE" 512)
  (setq ANG(getangle IP1 "\nPick direction of end of bolt ...O/S=near>"))
  (setvar "OSMODE" 0)
  (command ".UNDO" "GROUP")
  (setq D (getdist "\nEnter size of bolt (diameter) ...>")
        LEN (getdist "\nEnter length of bolt ...>")
        E (* D 1.8)
        K (* D 0.7)
        R1 D
        S (* D 1.35)
        P1 (polar IP1 (- ANG (* pi 0.5))(* E 0.5))
        P2 (polar IP1 (+ ANG (* pi 0.5))(* E 0.5))
        P3 (polar IP1 (+ ANG pi) K)
        P4 (polar P3 (- ANG (* pi 0.5))(* S 0.5))
        P5 (polar P3 (+ ANG (* pi 0.5))(* S 0.5))
        P6 (polar P3 ANG R1)
        P7 (polar P1 (+ ANG (* pi 0.5))(- E S))
        P8 (polar P2 (- ANG (* pi 0.5))(- E S))
        D3 (- (* E 0.5)(- E S))
        RP1 (polar P6 (- ANG (* pi 0.5)) D3)
        D1 (sqrt (- (* R1 R1)(* D3 D3)))
        D2 (- K (- R1 D1))
        P9 (polar RP1 (+ ANG pi) D1)
        P10 (polar (polar P6 (+ ANG (* pi 0.5)) D3)(+ ANG pi) D1)
        P11 (polar P1 (+ ANG pi) D2)
        P12 (polar P2 (+ ANG pi) D2)
        P13 (polar IP1 (- ANG (* pi 0.5))(* D 0.5))
        P14 (polar IP1 (+ ANG (* pi 0.5))(* D 0.5)))
  (cond ((< D 8)(> D 2)(setq PITCH 1))
        ((< D 24)(>= D 8)(setq PITCH 1.5))
        ((< D 27)(>= D 24)(setq PITCH 3.0))
        ((< D 33)(>= D 27)(setq PITCH 3.5))
        ((>= D 33)(setq PITCH 4.0))
  );cond
  (setq P15 (polar IP1 (+ ANG (* pi 0.5))(* (- D (* PITCH 1.5)) 0.5))
        P16 (polar IP1 (- ANG (* pi 0.5))(* (- D (* PITCH 1.5)) 0.5))
        P17 (polar P16 ANG LEN)
        P18 (polar P15 ANG LEN)
        P19 (polar P13 ANG (- LEN (* PITCH 0.5)))
        P20 (polar P14 ANG (- LEN (* PITCH 0.5)))
     );setq
  (setvar "BLIPMODE" 0)
  (if (= HD "H")
    (progn
      (command ".PLINE" P1 P11 "A" "S" P4 P9 "S" P3 P10 "S" P5 P12 "L" P2 "C")
      (command ".PLINE" P4 P5 "")
      (command ".PLINE" P9 P7 "")
      (command ".PLINE" P10 P8 "")
    );progn hex hd
  );if
  (if (= HD "S")
    (progn
      (setq A (* D 1.6)
            H D
            IP2 (polar IP1 (+ ANG pi) H)
            P21 (polar IP1 (- ANG (* pi 0.5)) (* A 0.5))
            P22 (polar IP1 (+ ANG (* pi 0.5)) (* A 0.5))
            P23 (polar P22 (+ ANG pi) (- H (* H 0.1)))
            P24 (polar P23 (- ANG (/ pi 2.0)) A)
            P25 (polar IP2 (- ANG (* pi 0.5)) (- (/ A 2.0) (* H 0.1)))
            P26 (polar IP2 (+ ANG (* pi 0.5)) (- (/ A 2.0) (* H 0.1)))
       );setq
      (command ".PLINE" P24 "W" 0 0 P21 P22 P23 P24 P25 P26 P23 "")
    );progn socket head
  );if
  (if (= HD "B")
    (progn
      (setq A (* D 1.9)
            H (/ D 1.5)
            IP2 (polar IP1 (+ ANG pi) H)
            P21 (polar IP1 (- ANG (* pi 0.5)) (* A 0.5))
            P22 (polar IP1 (+ ANG (* pi 0.5)) (* A 0.5))
            P23 (polar P22 (+ ANG pi) (* H 0.1))
            P24 (polar P23 (- ANG (/ pi 2.0)) A)
            P25 (polar IP2 (- ANG (* pi 0.5)) (- (/ A 2.25) (- H (* H 0.1))))
            P26 (polar IP2 (+ ANG (* pi 0.5)) (- (/ A 2.25) (- H (* H 0.1))))
       );setq
      (command ".PLINE" P21 "W" 0 0 P24 "A" P25 "")
        (setq E1 (entlast))
      (command ".PLINE" P21 P22 P23 "A" P26 "L" P25 "")
      (command ".PEDIT" "L" "J" E1 "" "")
      (command ".LINE" P23 P24 "")
    );progn button head
  );if
  (progn
    (command ".PLINE" P13 "W" 0 0 P19 P17 P18 P20 P14 "")
    (command ".PLINE" P16 P17 P19 P20 P18 P15 "")
  );progn threaded bolt
  (command ".UNDO" "END")
  (setvar "BLIPMODE" BLM)
  (setvar "OSMODE" OSM)
);defun
==============================================================
(defun C:ELEVHBOLT(/ IP1 IP2 D H HD LEN E K R1 S P1 P2 P3 P4 P5
 P6 P7 P8 P9 P10 P11 P12 P13 P14 P15 P16 P21 P22 P23 P24 P25 P26
 RP1 D1 D2)
  (command ".UNDO" "GROUP")
  (setq BLM (getvar "BLIPMODE")
        OSM (getvar "OSMODE"))
  (setvar "OSMODE" 32)
  (bl)
  (initget 1 "H S B")
  (setq HD(strcase(getkword "\nHex Socket or Button Head?  H,S,B ")))
  (setq IP1 (getpoint "\nPick insertion point of bolt ...O/S=int>"))
  (setvar "OSMODE" 512)
  (setq ANG(getangle IP1 "\nPick direction of end of bolt ...O/S=near>"))
  (setvar "OSMODE" 0)
  (setq D (getdist "\nEnter size of bolt (diameter) ...>")
        E (* D 1.8)
        K (* D 0.7)
        R1 D
        S (* D 1.35)
        P1 (polar IP1 (- ANG (* pi 0.5))(* E 0.5))
        P2 (polar IP1 (+ ANG (* pi 0.5))(* E 0.5))
        P3 (polar IP1 (+ ANG pi) K)
        P4 (polar P3 (- ANG (* pi 0.5))(* S 0.5))
        P5 (polar P3 (+ ANG (* pi 0.5))(* S 0.5))
        P6 (polar P3 ANG R1)
        P7 (polar P1 (+ ANG (* pi 0.5))(- E S))
        P8 (polar P2 (- ANG (* pi 0.5))(- E S))
        D3 (- (* E 0.5)(- E S))
        RP1 (polar P6 (- ANG (* pi 0.5)) D3)
        D1 (sqrt (- (* R1 R1)(* D3 D3)))
        D2 (- K (- R1 D1))
        P9 (polar RP1 (+ ANG pi) D1)
        P10 (polar (polar P6 (+ ANG (* pi 0.5)) D3)(+ ANG pi) D1)
        P11 (polar P1 (+ ANG pi) D2)
        P12 (polar P2 (+ ANG pi) D2)
        P13 (polar IP1 (- ANG (* pi 0.5))(* D 0.5))
        P14 (polar IP1 (+ ANG (* pi 0.5))(* D 0.5)))
  (cond ((< D 8)(> D 2)(setq PITCH 1))
        ((< D 24)(>= D 8)(setq PITCH 1.5))
        ((< D 27)(>= D 24)(setq PITCH 3.0))
        ((< D 33)(>= D 27)(setq PITCH 3.5))
        ((>= D 33)(setq PITCH 4.0))
  );cond
  (setq P15 (polar IP1 (+ ANG (* pi 0.5))(* (- D (* PITCH 1.5)) 0.5))
        P16 (polar IP1 (- ANG (* pi 0.5))(* (- D (* PITCH 1.5)) 0.5))
     );setq
  (setvar "BLIPMODE" 0)
  (if (= HD "H")
    (progn
      (command ".PLINE" P1 P11 "A" "S" P4 P9 "S" P3 P10 "S" P5 P12 "L" P2 "C")
      (command ".PLINE" P4 P5 "")
      (command ".PLINE" P9 P7 "")
      (command ".PLINE" P10 P8 "")
    );progn hex hd
  );if
  (if (= HD "S")
    (progn
      (setq A (* D 1.6)
            H D
            IP2 (polar IP1 (+ ANG pi) H)
            P21 (polar IP1 (- ANG (* pi 0.5)) (* A 0.5))
            P22 (polar IP1 (+ ANG (* pi 0.5)) (* A 0.5))
            P23 (polar P22 (+ ANG pi) (- H (* H 0.1)))
            P24 (polar P23 (- ANG (/ pi 2.0)) A)
            P25 (polar IP2 (- ANG (* pi 0.5)) (- (/ A 2.0) (* H 0.1)))
            P26 (polar IP2 (+ ANG (* pi 0.5)) (- (/ A 2.0) (* H 0.1)))
       );setq
      (command ".PLINE" P24 "W" 0 0 P21 P22 P23 P24 P25 P26 P23 "")
    );progn socket head
  );if
  (if (= HD "B")
    (progn
      (setq A (* D 1.9)
            H (/ D 1.5)
            IP2 (polar IP1 (+ ANG pi) H)
            P21 (polar IP1 (- ANG (* pi 0.5)) (* A 0.5))
            P22 (polar IP1 (+ ANG (* pi 0.5)) (* A 0.5))
            P23 (polar P22 (+ ANG pi) (* H 0.1))
            P24 (polar P23 (- ANG (/ pi 2.0)) A)
            P25 (polar IP2 (- ANG (* pi 0.5)) (- (/ A 2.25) (- H (* H 0.1))))
            P26 (polar IP2 (+ ANG (* pi 0.5)) (- (/ A 2.25) (- H (* H 0.1))))
       );setq
      (command ".PLINE" P21 "W" 0 0 P24 "A" P25 "")
        (setq E1 (entlast))
      (command ".PLINE" P21 P22 P23 "A" P26 "L" P25 "")
      (command ".PEDIT" "L" "J" E1 "" "")
      (command ".LINE" P23 P24 "")
    );progn button head
  );if
  (command ".UNDO" "END")
  (setvar "BLIPMODE" BLM)
  (setvar "OSMODE" OSM)
);defun
;=================================================
;bolt head plan
(defun C:HEXHEAD (/ IP1 D S)
  (command ".UNDO" "GROUP")
  (setq OSM (getvar "OSMODE"))
  (setvar "OSMODE" 32)
  (bl)
  (setq IP1 (getpoint "\nPick insertion point of bolt ...O/S=int>"))
  (setvar "OSMODE" 0)
  (setq D (getdist "\nEnter size of bolt (thread diameter) ...>"))
  (setq S (* D 1.6))
  (progn
    (command ".CIRCLE" IP1 "D" (* S 0.95))
    (command ".CIRCLE" IP1 "D" (* S 1.25))
    (command ".POLYGON" 6 IP1 "C" (* S 0.5))
  );progn
  (command ".UNDO" "END")
  (setvar "OSMODE" OSM)
)
;=================================================
;spring rollpin plan
(defun C:ROLLPIN (/ IP1 P1 P2 P3 P4 D1 D S)
  (command ".UNDO" "GROUP")
  (setq OSM (getvar "OSMODE"))
  (setvar "OSMODE" 32)
  (bl)
  (setq IP1 (getpoint "\nPick centre point of rollpin ...O/S=int>"))
  (setvar "OSMODE" 0)
  (setq D (getdist "\nEnter size of Rollpin (o/diameter) ...>")
        S (* D 0.5)
        D1(* D 0.25)
        P1 (polar IP1 (dtr 170) S)
        P2 (polar IP1 (dtr 170) D1)
        P3 (polar IP1 (dtr 150) S)
        P4 (polar IP1 (dtr 150) D1)
        P5 (polar P1 0 0.5))
  (progn
    (command ".ARC" "C" IP1 P2 "A" "340")
    (setq E1 (entlast))
    (command ".ARC" "C" IP1 P1 "A" "340")
    (setq E2 (entlast))
    (command ".LINE" P3 P4 "")
    (setq E3 (entlast))
    (command ".PLINE" P1 P2 "")
    (command ".PEDIT" "L" "J" E1  E2  E3 "" "")
;    (command ".OFFSET" "0.75" "L" P5)
  );progn
  (command ".UNDO" "END")
  (setvar "OSMODE" OSM)
)
;=================================================
;hexnut plan
(defun C:HEXHEADNUT (/ D S IP1 TD R)
  (command ".UNDO" "GROUP")
  (setq OSM (getvar "OSMODE"))
  (setvar "OSMODE" 32)
  (bl)
  (setq IP1 (getpoint "\nPick insertion point of nut ...O/S=int>"))
  (setvar "OSMODE" 0)
  (setq D (getreal "\nEnter size of nut (thread diameter) ...>"))
  (setq S (* D 1.6))
  (cond ((< D 8)(> D 2)(setq PITCH 1))
        ((< D 24)(>= D 8)(setq PITCH 1.5))
        ((< D 27)(>= D 24)(setq PITCH 3.0))
        ((< D 33)(>= D 27)(setq PITCH 3.5))
        ((>= D 33)(setq PITCH 4.0))
  )
  (setq TD (- D (* PITCH 1.5)))
  (setq R (* TD 0.5))
  (setq BLM (getvar "BLIPMODE"))
  (setvar "BLIPMODE" 0)
  (progn
    (command ".CIRCLE" IP1 "D" (* S 0.95))
    (command ".CIRCLE" IP1 "D" D)
    (command ".CIRCLE" IP1 "D" (* S 1.20))
    (command ".POLYGON" 6 IP1 "C" (* S 0.5))
    (command ".ARC" "C" IP1 (strcat "@" (rtos R 2 2) "<90") "A" "270")
  );progn
  (setvar "BLIPMODE" BLM)
  (setvar "OSMODE" OSM)
  (command ".UNDO" "END")
);defun
;=================================================
;tapped hole plan
(defun C:TAPHOLE (/ D IP1 TD R)
  (command ".UNDO" "GROUP")
  (setq OSM (getvar "OSMODE"))
  (setvar "OSMODE" 32)
  (bl)
  (setq IP1 (getpoint "\nPick insertion point for hole ...O/S=int>"))
  (setvar "OSMODE" 0)
  (setq D (getreal "\nEnter size of thread (diameter) ...>"))
  (cond ((< D 8)(> D 2)(setq PITCH 1))
        ((< D 24)(>= D 8)(setq PITCH 1.25))
        ((< D 27)(>= D 24)(setq PITCH 3.0))
        ((< D 33)(>= D 27)(setq PITCH 3.5))
        ((>= D 33)(setq PITCH 4.0))
  )
  (setq TD (- D (* PITCH 1.5)))
  (setq R (* D 0.5))
  (setq BLM (getvar "BLIPMODE"))
  (setvar "BLIPMODE" 0)
  (progn
    (command ".CIRCLE" IP1 "D" TD)
    (command ".ARC" "C" IP1 (strcat "@" (rtos R 2 2) "<90") "A" "270")
  );progn
  (setvar "BLIPMODE" BLM)
  (setvar "OSMODE" OSM)
  (command ".UNDO" "END")
);defun
;=================================================
;thread plan
(defun C:THRDEND (/ D IP1 TD R)
  (command ".UNDO" "GROUP")
  (setq OSM (getvar "OSMODE"))
  (setvar "OSMODE" 32)
  (bl)
  (setq IP1 (getpoint "\nPick insertion point for thread ...O/S=int>"))
  (setvar "OSMODE" 0)
  (setq D (getreal "\nEnter size of thread (diameter) ...>"))
  (cond ((< D 8)(> D 2)(setq PITCH 1))
        ((< D 24)(>= D 8)(setq PITCH 1.25))
        ((< D 27)(>= D 24)(setq PITCH 3.0))
        ((< D 33)(>= D 27)(setq PITCH 3.5))
        ((>= D 33)(setq PITCH 4.0))
  )
  (setq TD (- D (* PITCH 1.5)))
  (setq R (* TD 0.5))
  (setq BLM (getvar "BLIPMODE"))
  (setvar "BLIPMODE" 0)
  (progn
    (command ".CIRCLE" IP1 "D" D)
    (command ".ARC" "C" IP1 (strcat "@" (rtos R 2 2) "<90") "A" "270")
  );progn
  (setvar "BLIPMODE" BLM)
  (setvar "OSMODE" OSM)
  (command ".UNDO" "END")
);defun
;=================================================
;rooftop hexnut elevation
(defun C:RHEXNUT (/ IP1 IP2 IP3 IP4 D E S R1 P1 P2 P3 P4 P5 P6 P7
 P8 P9 P10 P11 P12 P13 P14 P15 P16)
  (command ".UNDO" "GROUP")
  (setq OSM (getvar "OSMODE"))
  (setvar "OSMODE" 32)
  (setq PB (getvar "PICKBOX"))
  (bl)
  (setq IP1 (getpoint "\nPick insertion point of nut ...O/S=int>"))
  (setvar "OSMODE" 256)
  (setq ANG (getangle IP1 "\nDirection of opposite face ...>"))
  (setvar "OSMODE" 0)
  (setq D (getdist "\nEnter size of nut (thread diameter) ...>"))
  (setq E (* D 1.8)
        S (* D 1.35)
        R1 D
        K (* D 0.9))
  (setq P1 (polar IP1 (+ ANG(* pi 0.5))(* D 1.20))
        IP2 (polar IP1 ANG(* D 0.25))
        P2 (polar IP2 (+ ANG(* pi 0.5))(* D 0.95))
        IP3 (polar IP1 ANG(- K(* D 0.11)))
        P3 (polar IP3 (+ ANG(* pi 0.5))(* D 0.95))
        IP4 (polar IP1 ANG K)
        P4 (polar IP4 (+ ANG(* pi 0.5))(* D 0.84))
        P5 (polar IP4 (- ANG(* pi 0.5))(* D 0.84))
        P6 (polar IP3 (- ANG(* pi 0.5))(* D 0.95))
        P7 (polar IP2 (- ANG(* pi 0.5))(* D 0.95))
        P8 (polar IP1 (- ANG(* pi 0.5))(* D 1.20))
        P9 (polar IP2 (+ ANG(* pi 0.5))(* D 0.525))
        P10 (polar IP3 (+ ANG(* pi 0.5))(* D 0.525))
        P11 (polar IP3 (- ANG(* pi 0.5))(* D 0.525))
        P12 (polar IP2 (- ANG (* pi 0.5))(* D 0.525))
        P13 (polar IP1 (+ ANG(* pi 0.5))(* D 0.7375))
        P14 (polar IP1 (- ANG(* pi 0.5))(* D 0.7375))
        P15 (polar IP4 (+ ANG(* pi 0.5))(* D 0.7375))
        P16 (polar IP4 (- ANG(* pi 0.5))(* D 0.7375))
        BLM (getvar "BLIPMODE"))
  (setvar "BLIPMODE" 0)
  (setvar "PICKBOX" 1)
  (progn
    (command ".PLINE" P1 "W" 0 0 P2 P3 P4 P5 P6 P7 P8 "C")
    (command ".TRIM" (entlast) "" P9 P12 "")
    (command ".PLINE" P6 "A" "S" P16 P11 "S" IP4 P10 "S" P15 P3 "")
    (command ".COPY" (entlast) "" P3 P2)
    (command ".PLINE" P9 P10 "")
    (command ".PLINE" P12 P11 "")
  );progn
  (setvar "BLIPMODE" BLM)
  (setvar "OSMODE" OSM)
  (setvar "PICKBOX" PB)
  (command ".UNDO" "END")
);defun
;=================================================
;hexnut elevation
(defun C:HEXNUT (/ IP1 IP2 IP3 IP4 D THK E S R1 P1 P2 P3 P4 P5 P6 P7
 P8 P9 P10 P11 P12 P13 P14 P15 P16)
  (command ".UNDO" "GROUP")
  (setq OSM (getvar "OSMODE"))
  (setvar "OSMODE" 32)
  (setq PB (getvar "PICKBOX"))
  (bl)
  (setq IP1 (getpoint "\nPick insertion point of nut ...O/S=int>"))
  (setvar "OSMODE" 512)
  (setq ANG (getangle IP1 "\nDirection of opposite face ...O/S=near>"))
  (setvar "OSMODE" 0)
  (setq D (getdist "\nEnter size of nut (thread diameter) ...>"))
  (initget 1 "P T")
  (setq THK (strcase(getkword "\nPlain or Thin nut (P/T) ..."))
        E (* D 1.8)
        S (* D 1.35)
        R1 D)
    (if (= "P" THK)
        (setq K (* D 0.8))
        (setq K (* D 0.5))
    );if
  (setq P1 (polar IP1 (+ ANG(* pi 0.5))(* D 0.84))
        IP2 (polar IP1 ANG(* D 0.11))
        P2 (polar IP2 (+ ANG(* pi 0.5))(* D 0.95))
        IP3 (polar IP1 ANG(- K(* D 0.11)))
        P3 (polar IP3 (+ ANG(* pi 0.5))(* D 0.95))
        IP4 (polar IP1 ANG K)
        P4 (polar IP4 (+ ANG(* pi 0.5))(* D 0.84))
        P5 (polar IP4 (- ANG(* pi 0.5))(* D 0.84))
        P6 (polar IP3 (- ANG(* pi 0.5))(* D 0.95))
        P7 (polar IP2 (- ANG(* pi 0.5))(* D 0.95))
        P8 (polar IP1 (- ANG(* pi 0.5))(* D 0.84))
        P9 (polar IP2 (+ ANG(* pi 0.5))(* D 0.525))
        P10 (polar IP3 (+ ANG(* pi 0.5))(* D 0.525))
        P11 (polar IP3 (- ANG(* pi 0.5))(* D 0.525))
        P12 (polar IP2 (- ANG (* pi 0.5))(* D 0.525))
        P13 (polar IP1 (+ ANG(* pi 0.5))(* D 0.7375))
        P14 (polar IP1 (- ANG(* pi 0.5))(* D 0.7375))
        P15 (polar IP4 (+ ANG(* pi 0.5))(* D 0.7375))
        P16 (polar IP4 (- ANG(* pi 0.5))(* D 0.7375))
        BLM (getvar "BLIPMODE"))
  (setvar "BLIPMODE" 0)
  (setvar "PICKBOX" 1)
  (progn
    (command ".PLINE" P1 "W" 0 0 P2 P3 P4 P5 P6 P7 P8 "C")
    (command ".TRIM" (entlast) "" P9 P12 "")
    (command ".PLINE" P2 "A" "S" P13 P9 "S" IP1 P12 "S" P14 P7 "")
    (command ".PLINE" P6 "A" "S" P16 P11 "S" IP4 P10 "S" P15 P3 "")
    (command ".PLINE" P9 P10 "")
    (command ".PLINE" P12 P11 "")
  );progn
  (setvar "BLIPMODE" BLM)
  (setvar "OSMODE" OSM)
  (setvar "PICKBOX" PB)
  (command ".UNDO" "END")
);defun
;=================================================
(defun C:SHEADCAP (/ IP1 D S A CHAM)
  (command ".UNDO" "GROUP")
  (setq OSM (getvar "OSMODE"))
  (setvar "OSMODE" 32)
  (bl)
  (setq IP1 (getpoint "\nPick insertion point of Cap Screw ...O/S=int>"))
  (setvar "OSMODE" 0)
  (setq D (getreal "\nEnter size of bolt (thread diameter) ...>"))
  (setq S (* D 0.8)
        A (* D 1.6))
  (setq BLM (getvar "BLIPMODE"))
  (setvar "BLIPMODE" 0)
  (cond ((< D 5) (> D 2) (setq CHAM 0.5))
        ((< D 8) (> D 5) (setq CHAM 1.0))
        ((< D 24) (> D 8) (setq CHAM 2.0))
        ((< D 27) (> D 24) (setq CHAM 3.0))
        ((> D 27) (setq CHAM 4.0))
  );cond
  (setq C (- A CHAM))
  (progn
    (command ".CIRCLE" IP1 "D" S)
    (command ".CIRCLE" IP1 "D" (* A 0.85))
    (command ".CIRCLE" IP1 "D" A)
    (command ".POLYGON" 6 IP1 "C" (* S 0.5))
  );progn
  (setvar "BLIPMODE" BLM)
  (setvar "OSMODE" OSM)
  (command ".UNDO" "END")
);defun
;=================================================
;spring or flat washer
(defun C:SPWASH (/ IP1 IP2 D THK P1 P2 P3 P4 P5 P6 P7 P8)
  (command ".UNDO" "GROUP")
  (setq BLM (getvar "BLIPMODE"))
  (setvar "BLIPMODE" 0)
  (setq OSM (getvar "OSMODE"))
  (setvar "OSMODE" 32)
  (bl)
  (setq IP1 (getpoint "\nPick insertion point of washer ...O/S=int>"))
  (setvar "OSMODE" 512)
  (setq IP2 (getpoint IP1 "\nDirection of opposite face ...O/S=near>")
        ANG (angle IP1 IP2))
  (setvar "OSMODE" 0)
  (setq D (getdist "\nEnter size of nut (thread diameter) ...>"))
  (initget 1 "P S")
  (setq THK (strcase(getkword "\nPlain or Spring Washer (P/S) ...")))
    (if (= "S" THK)
        (setq THK (* D 0.2) R 0.95)
        (setq THK (* D 0.12) R 1.0)
    );if
  (setq P1 (polar IP1(+ ANG(* pi 0.5))(* D R))
        P2 (polar P1 ANG THK)
        P3 (polar IP1(- ANG(* pi 0.5))(* D R))
        P4 (polar P3 ANG THK)
        P5 (polar IP1 ANG THK)
        P6 (polar IP1(+ ANG(* pi 0.5)) THK)
        P7 (polar P5 (- ANG(* pi 0.5))(* THK 0.5))
        P8 (polar IP1 (+ ANG(* pi 0.5))(* THK 0.5))
   )
 (command ".PLINE" P1 "W" 0 0 P2 P4 P3 "C")
    (if (< R 1)
      (progn
        (command ".LINE" P7 P8 "")
        (command ".LINE" P6 P5 "")
      );progn
    );if
  (setvar "BLIPMODE" BLM)
  (setvar "OSMODE" OSM)
  (command ".UNDO" "END")
);defun
(princ) ; sshhhh
;=================================================
