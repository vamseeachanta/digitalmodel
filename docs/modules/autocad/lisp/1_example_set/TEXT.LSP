(DEFUN C:Txt()
(setq a 0)
(prompt "...        Select Your Text Please      ...")
(setq ent1 (ssget '((0 . "text"))))
(setq num (sslength ent1))
(setq cnt 0)
(repeat num
(setq s1 (ssname ent1 cnt))
(setq s2 (entget s1))
(setq txt (cdr (assoc 1 s2)))
(setq rtxt (atof txt))
(setq a (+ a rtxt))
(setq cnt (1+ cnt))
)
(princ "Total Area=")
(setq sa (rtos a 2 2))
(princ sa)
(setq a 0)
(princ)
)
