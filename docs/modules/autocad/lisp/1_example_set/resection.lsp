(defun c:bint (/ a b c d e f g1 h1 i1 g h i c1 c2 m e1 e2 n d1 f1 v m n )
(setq obm (getvar "blipmode")) 
(setq osmd (getvar "osmode"))
(setq andr(getvar"angdir"))
(setq dimun(getvar"dimaunit"))
(setq andb(getvar"angbase")) 
(setq aunt(getvar"aunits"))  
(setvar"dimadec"4)
(setq clyr(getvar"clayer"))
;;;;;;;;;;;;;;;;;;;;;;;;;;;;;;;
(if(null angsys)
    (setq angsys 0))
  (setq angsysnew(getreal(strcat"\n choose angular system<1> for grads<0>for degrees:"   "<"(rtos angsys 2 0)">:")))
(if angsysnew(setq angsys angsysnew))
       ;;;;;;;;;;;;;;;;;;;;;;;;
(if(= angsys 0)
  (progn
(initget "Click Enter")
(setq x (getkword "\n Click points or Entering coordinates<C or E>:"))
      (if (= x "Enter")
	(progn
	  (setq a (getreal "\n enter x1: ")
      b (getreal "\n enter y1: ")
      c (getreal "\n enter x2: ")
      d (getreal "\n enter y2: ")
      e (getreal "\n enter x3: ")
      f (getreal "\n enter y3: ")
      gdg(getreal"\enter An1(decimal degree angle):")
      h1dg(getreal"\n enter An2(decimal degree angle):")		
      g1(/(* gdg 400)360)
      h1(/(* h1dg 400)360)
      i1(- 400(+ g1 h1))
      g (/(* g1 pi)200)
      h (/(* h1 pi)200)
      i (/(* i1 pi)200)
     )

(setvar "angdir"1)	
(setvar "angbase"(/ pi 2))	
(setvar "aunits"2)
(setvar "dimaunit"2)	  
(setq pn1(list a b)pn2(list c d)pn3(list e f))
	  
(setq c1 (/(- c a)(- d b))
      c2 (/(- e a)(- f b))
      m (-(atan c1)(atan c2))
      )
(setq e1 (/(- e c)(- f d))
      e2 (/(- a c)(- b d))
      n (-(atan e1)(atan e2))
      )
(setq d1 (*(- d b)(- f b))
      f1 (*(- f d)(- b d))
      )
(cond
  ((and(<= f1 0))
   (setq v (+ n pi)))
(t(setq v n))
  )
(cond
  ((and(<= d1 0))
   (setq u (+ m pi)))
  (t(setq u m))
  )
  (setq w (- pi(+ u v)))
(setq tgu (/(sin u)(cos u))
      tgg (/(sin g)(cos g))
      tgv (/(sin v)(cos v))
      tgh (/(sin h)(cos h))
      tgw (/(sin w)(cos w))
      tgi (/(sin i)(cos i))
      )
(setq p (/ 1(-(/ 1 tgu)(/ 1 tgg)))
      q (/ 1(-(/ 1 tgv)(/ 1 tgh)))
      r (/ 1(-(/ 1 tgw)(/ 1 tgi)))
      )
(setq x (/(+(+(* a p)(* c q))(* e r))(+(+ p q)r)))
(setq y (/(+(+(* b p)(* d q))(* f r))(+(+ p q)r)))
(terpri)
(princ "x=")
(princ (rtos x 2 3))
(terpri)
(princ "y=")
(princ (rtos y 2 3))
(terpri)
(print "end")
	  (setq pnix(list x y))
	  (command "line" pnix pn1 "")
	  (command "line" pnix pn2 "")
	  (command "line" pnix pn3 "")

     (setvar"osmode"0)
     (command"point"(list x y))
     (command"text"pnix 20 100 (rtos x 2 3))
     (command"text"(list(car pnix)(-(cadr pnix)23)) 20 100 (rtos y 2 3))
     
(setvar"angbase"andb)
(setvar "angdir"andr)
(setvar"aunits"aunt)
(setvar"dimaunit"dimun)	  
(setvar "osmode" osmd)
(setvar"clayer"clyr)	  
(alert (strcat"X="(rtos x 2 3)" @ " "Y="(rtos Y 2 3)))	  
)
	)
  
  (if (= x "Click")
	(progn
       
     (setq pot1(getpoint "\n click first point"))
     (setq pot2(getpoint "\n click second point"))
     (setq pot3(getpoint "\n click third point"))
     (setq osmd(getvar"osmode"))
     (setq a (car pot1)
      b (cadr pot1)
      c (car pot2)
      d (cadr pot2)
      e (car pot3)
      f (cadr pot3))

(setq
      gdg(getreal"\n enter An1(decimal degree angle):")
      h1dg(getreal"\n enter An2(decimal degree angle):")
      g1(/(* gdg 400)360)
      h1(/(* h1dg 400)360)
      i1(- 400(+ g1 h1))
      g (/(* g1 pi)200)
      h (/(* h1 pi)200)
      i (/(* i1 pi)200)
     )

(setvar "angdir"1)	
(setvar "angbase"(/ pi 2))	
(setvar "aunits"2)
(setvar "dimaunit"2)    
(setq c1 (/(- c a)(- d b))
      c2 (/(- e a)(- f b))
      m (-(atan c1)(atan c2))
      )
(setq e1 (/(- e c)(- f d))
      e2 (/(- a c)(- b d))
      n (-(atan e1)(atan e2))
      )
(setq d1 (*(- d b)(- f b))
      f1 (*(- f d)(- b d))
      )
(cond
  ((and(<= f1 0))
   (setq v (+ n pi)))
(t(setq v n))
  )
(cond
  ((and(<= d1 0))
   (setq u (+ m pi)))
  (t(setq u m))
  )
  (setq w (- pi(+ u v)))
(setq tgu (/(sin u)(cos u))
      tgg (/(sin g)(cos g))
      tgv (/(sin v)(cos v))
      tgh (/(sin h)(cos h))
      tgw (/(sin w)(cos w))
      tgi (/(sin i)(cos i))
      )
(setq p (/ 1(-(/ 1 tgu)(/ 1 tgg)))
      q (/ 1(-(/ 1 tgv)(/ 1 tgh)))
      r (/ 1(-(/ 1 tgw)(/ 1 tgi)))
      )
(setq x (/(+(+(* a p)(* c q))(* e r))(+(+ p q)r)))
(setq y (/(+(+(* b p)(* d q))(* f r))(+(+ p q)r)))
(setq pinte(list x y))
     (setvar"osmode"0)
     (command"point"(list x y))
     (command"text"pinte 20 100 (rtos x 2 3))
     (command"text"(list(car pinte)(-(cadr pinte)23)) 20 100 (rtos y 2 3))
     (command"line"pot1 pinte pot2 "")
     (command"line"pinte pot3"")
     (setvar"osmode"osmd)
(terpri)
(princ "x=")
(princ (rtos x 2 3))
(terpri)
(princ "y=")
(princ (rtos y 2 3))
(terpri)
(print "end")
 (setvar"angbase"andb)
 (setvar "angdir"andr)
 (setvar"aunits"aunt)
 (setvar"dimaunit"dimun)    
 (setvar "osmode" osmd)
 (setvar"clayer"clyr)  
 (alert (strcat"X="(rtos x 2 3)" @ " "Y="(rtos Y 2 3)))   
)
    )
)
    )

  ;;;;;;;;;;;;;;;;mmmmmmmmmmmmmeeeeeeeeeeeeeeeeeeeeeeeeeeeeeeeeeeeeeeeeeeeeeeeeeeeeeeeee
  
  (if(= angsys 1)
    (progn
(initget "Click Enter")
(setq x (getkword "\n Click points or Entering coordinates<C or E>:"))
      (if (= x "Enter")
	(progn
	  (setq a (getreal "\n enter x1: ")
      b (getreal "\n enter y1: ")
      c (getreal "\n enter x2: ")
      d (getreal "\n enter y2: ")
      e (getreal "\n enter x3: ")
      f (getreal "\n enter y3: ")
      g1(getreal "\n enter An1(grad): ")
      h1(getreal "\n enter An2(grad): ")
      i1(- 400(+ g1 h1))
      
      g (/(* g1 pi)200)
      h (/(* h1 pi)200)
      i (/(* i1 pi)200)
     )
(setvar "angdir"1)	
(setvar "angbase"(/ pi 2))	
(setvar "aunits"2)
(setvar "dimaunit"2)
	  (setq pn1(list a b)pn2(list c d)pn3(list e f))
	  
(setq c1 (/(- c a)(- d b))
      c2 (/(- e a)(- f b))
      m (-(atan c1)(atan c2))
      )
(setq e1 (/(- e c)(- f d))
      e2 (/(- a c)(- b d))
      n (-(atan e1)(atan e2))
      )
(setq d1 (*(- d b)(- f b))
      f1 (*(- f d)(- b d))
      )
(cond
  ((and(<= f1 0))
   (setq v (+ n pi)))
(t(setq v n))
  )
(cond
  ((and(<= d1 0))
   (setq u (+ m pi)))
  (t(setq u m))
  )
  (setq w (- pi(+ u v)))
(setq tgu (/(sin u)(cos u))
      tgg (/(sin g)(cos g))
      tgv (/(sin v)(cos v))
      tgh (/(sin h)(cos h))
      tgw (/(sin w)(cos w))
      tgi (/(sin i)(cos i))
      )
(setq p (/ 1(-(/ 1 tgu)(/ 1 tgg)))
      q (/ 1(-(/ 1 tgv)(/ 1 tgh)))
      r (/ 1(-(/ 1 tgw)(/ 1 tgi)))
      )
(setq x (/(+(+(* a p)(* c q))(* e r))(+(+ p q)r)))
(setq y (/(+(+(* b p)(* d q))(* f r))(+(+ p q)r)))
(terpri)
(princ "x=")
(princ (rtos x 2 3))
(terpri)
(princ "y=")
(princ (rtos y 2 3))
(terpri)
(print "end")
	  (setq pnix(list x y))
	  (command "line" pnix pn1 "")
	  (command "line" pnix pn2 "")
	  (command "line" pnix pn3 "")

     (setvar"osmode"0)
     (command"point"(list x y))
     (command"text"pnix 20 100 (rtos x 2 3))
     (command"text"(list(car pnix)(-(cadr pnix)23)) 20 100 (rtos y 2 3))
     
(setvar"angbase"andb)
(setvar "angdir"andr)
(setvar"aunits"aunt)
(setvar "osmode" osmd)
(setvar"clayer"clyr)	  
(alert (strcat"X="(rtos x 2 3)" @ " "Y="(rtos Y 2 3)))	  
)
	)
  
  (if (= x "Click")
	(progn
       
     (setq pot1(getpoint "\n click first point"))
     (setq pot2(getpoint "\n click second point"))
     (setq pot3(getpoint "\n click third point"))
     (setq osmd(getvar"osmode"))
     (setq a (car pot1)
      b (cadr pot1)
      c (car pot2)
      d (cadr pot2)
      e (car pot3)
      f (cadr pot3))

(setq g1(getreal "\n enter An1(grad): ")
      h1(getreal "\n enter An2(grad): ")
      i1(- 400(+ g1 h1))
      g (/(* g1 pi)200)
      h (/(* h1 pi)200)
      i (/(* i1 pi)200)
     )
(setvar "angdir"1)	
(setvar "angbase"(/ pi 2))	
(setvar "aunits"2)
(setvar "dimaunit"2)
(setq c1 (/(- c a)(- d b))
      c2 (/(- e a)(- f b))
      m (-(atan c1)(atan c2))
      )
(setq e1 (/(- e c)(- f d))
      e2 (/(- a c)(- b d))
      n (-(atan e1)(atan e2))
      )
(setq d1 (*(- d b)(- f b))
      f1 (*(- f d)(- b d))
      )
(cond
  ((and(<= f1 0))
   (setq v (+ n pi)))
(t(setq v n))
  )
(cond
  ((and(<= d1 0))
   (setq u (+ m pi)))
  (t(setq u m))
  )
  (setq w (- pi(+ u v)))
(setq tgu (/(sin u)(cos u))
      tgg (/(sin g)(cos g))
      tgv (/(sin v)(cos v))
      tgh (/(sin h)(cos h))
      tgw (/(sin w)(cos w))
      tgi (/(sin i)(cos i))
      )
(setq p (/ 1(-(/ 1 tgu)(/ 1 tgg)))
      q (/ 1(-(/ 1 tgv)(/ 1 tgh)))
      r (/ 1(-(/ 1 tgw)(/ 1 tgi)))
      )
(setq x (/(+(+(* a p)(* c q))(* e r))(+(+ p q)r)))
(setq y (/(+(+(* b p)(* d q))(* f r))(+(+ p q)r)))
(setq pinte(list x y))
     (setvar"osmode"0)
     (command"point"(list x y))
     (command"text"pinte 20 100 (rtos x 2 3))
     (command"text"(list(car pinte)(-(cadr pinte)23)) 20 100 (rtos y 2 3))
     (command"line"pot1 pinte pot2 "")
     (command"line"pinte pot3"")
     (setvar"osmode"osmd)
(terpri)
(princ "x=")
(princ (rtos x 2 3))
(terpri)
(princ "y=")
(princ (rtos y 2 3))
(terpri)
(print "end")
 (setvar"angbase"andb)
 (setvar "angdir"andr)
 (setvar"aunits"aunt)
 (setvar "osmode" osmd)
 (setvar"clayer"clyr)  
 (alert (strcat"X="(rtos x 2 3)" @ " "Y="(rtos Y 2 3)))   
)
    )	  
)
)
  )
