;;;routine to output the coordinates of a selection set of point entities#     
;;;coded by imran june 2002
(defun c:points ()
    (setq dimzin_var (getvar "DIMZIN"))
  (setvar "DIMZIN" 1)
  (setvar "CMDECHO" 0)
(setq data_file (getfiled "Select Data File" "" "csv" 11 )) 
     (setq f (open data_file "w"))
     (write-line "Point mark,N,E" f)
     (command "ucs" "new" "V")
     (setq sched_ip (getpoint "\nPick Schedule origin : "))  
     (setq x_orig (car sched_ip))
     (setq y_orig (cadr sched_ip))
     (command "ucs" "Prev")
     
     (setq t_hgt (getvar "TEXTSIZE"))
     (if (= t_hgt 0.0)
       (setq t_hgt (getreal "\nEnter Text Height : "))
                                                         )
     (setq col_width (* 20.0 t_hgt))
     (setq col_height (* 2.0 t_hgt))
     (setq def_convert_kw "Y")
     (setq convert_kw (getstring "\Convert millimetres to metres (Yes/No) <Yes> : "))
     (if (= convert_kw "") (setq convert_kw def_convert_kw) )
     (setq convert_kw (substr (strcase convert_kw) 1 1))
     (setq blk_name (getstring "\nEnter Setting Out Point block name : "))
     (princ "\nSelect Setting Out Blocks :")
;     (setq node_ss (ssget  '( (2 . "SOP")
     (setq node_ss (ssget  (list (cons 2 blk_name))
                           )
                  
                  )
     (setq cnt (getint "\nEnter start number for sequence : <1> "))
     (if (= cnt nil) (setq cnt 1))
     (setq node_ss_len (sslength node_ss))
     (setq i 0)
     (repeat node_ss_len 
         (setq en (ssname node_ss i))
         (setq endat (entget en))
;write point reference on drawing
         (setq t_ip (cdr (assoc 10 endat)))
         (setq txt_ang (- 0.0 (getvar "VIEWTWIST")))
         (setq t_str (strcat "P" (itoa cnt)))
         (txt_bl)
       (command "ucs" "new" "v")
         (if (= convert_kw "Y")
	   (setq x_node_coord (/ (cadr (assoc 10 endat)) 1000.0))
	   (setq x_node_coord (cadr (assoc 10 endat)))
	                           )
	 (if (= convert_kw "Y")  
           (setq y_node_coord (/ (caddr (assoc 10 endat)) 1000.0))
	   (setq y_node_coord (caddr (assoc 10 endat)))
	                            )
         (setq X_coord_txt (rtos x_node_coord 2 3))
         (setq Y_coord_txt (rtos y_node_coord 2 3))
;write text in schedule
;Headers
         (setq x_ip x_orig)
         (setq y_ip (+ y_orig col_height))
         (setq t_ip (trans (list x_ip y_ip) 2 0))
         (setq t_str "POINT REFERENCE")
         (txt_bl)
         (setq x_ip (+ x_orig col_width))
         (setq t_ip (trans (list x_ip y_ip) 2 0))
         (setq t_str "NORTHING")
         (txt_bl)
         (setq x_ip (+ x_orig (* 2.0 col_width)))
         (setq t_ip (trans (list x_ip y_ip) 2 0))
         (setq t_str "EASTING")
         (txt_bl)
       
;reference no.       
         (setq x_ip x_orig)
         (setq y_ip (- y_orig (* i col_height)))
         (setq t_ip (trans (list x_ip y_ip) 2 0))
         (setq t_str (strcat "P" (itoa cnt)))
         (txt_bl)
;Northing
         (setq x_ip (+ x_orig col_width))
         (setq t_ip (trans (list x_ip y_ip) 2 0))
         (setq t_str Y_coord_txt)
         (txt_bl)
;easting
         (setq x_ip (+ x_orig (* 2.0 col_width)))
	 (setq t_ip (trans (list x_ip y_ip) 2 0))
         (setq t_str X_coord_txt)
	 (txt_bl)
       (command "ucs" "prev")
;write text to file
         (setq coord_txt (strcat "P" (itoa cnt) "," Y_coord_txt "," X_coord_txt))
         (write-line coord_txt f)

         (setq i (+ i 1))
         (setq cnt (+ cnt 1))
                          )
    (close f)
  (setvar "DIMZIN" dimzin_var)
  (princ)
)         


(defun txt_bl ()
 (setq e_msg "Error creating text")
 (setq t_style (getvar "TEXTSTYLE"))
 (if (= t_hgt nil) (setq t_hgt 62.5))
 (entmake (list  (cons 0 "TEXT")            
;             (cons 8 "TEXT")            
;             (cons 6 "CONTINUOUS")
             (list 10 0.0 0.0 0.0)         
             (cons 40 t_hgt)        
             (cons 1 t_str)
             (cons 50 txt_ang)
             (cons 51 0.0)
             (cons 62 7)
             (cons 7 t_style) 
             (cons 71 0)
             (cons 72 0)
             (list 11 0.0 0.0 0.0) 
             (list 210 0.0 0.0 1.0)
             (cons 73 1)         
                     )
                     )
  


  (setq en (entlast))
(setq ed (entget en))
(setq ed (subst (cons 11 t_ip)
                (assoc 11 ed)
                           ed
                 )
             )

(entmod ed)
(entupd en)
  ); end defun txt_bl
