(defun C:SET()
;(defun *ERROR* (MSG)
;       (princ "error: ")
;       (princ msg)
;       (terpri)
;)
	(setvar "cmdecho" 0)
	(setq fnam (getSTRING"\nENTER FILE NAME:"))
	(setq rext ".CON")
	(setq rcfnam (strcat fnam rext))
	(graphscr)
(princ "                              Working ... Please Wait!")
		(command "color" 4)
		(command "ucsicon" "off")
		(setq i (open rcfnam "r"))
(SETQ CNT 0)
(if i
	(progn
		(while (setq pnt (read-line i))
			(SETQ CNT (1+ CNT))
			(SETQ X (SUBSTR PNT 16 7))
			(SETQ Y (SUBSTR PNT 28 7))
			(SETQ Z (SUBSTR PNT 38 6))
			(SETQ FLG (SUBSTR PNT 46 1))
			(SETQ FLG (ATOI FLG))
			(SETQ NPNT (STRCAT X "," Y "," Z))
			(if (= cnt 1) (setq pntp npnt))
			(IF (= FLG 2)
				(PROGN
				(SETQ CNT 0)
				(COMMAND "LINE" PNTP PNTP C)
				)
			)
			(IF (/= CNT 1)
				(PROGN
				(IF (/= FLG 2)
					(PROGN
					(command "line" PNTP Npnt "") 
					(setq pntp Npnt) 
					)
				)       
				)
			)
		)
	)
)
(close i)
;(command "zoom" "a")
)
