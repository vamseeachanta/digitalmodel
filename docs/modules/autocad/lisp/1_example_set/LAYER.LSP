;; LAYER.LSP Version 2.1, Copyright (C) 1997 by Pham Hoang Anh, K37.X6
;; ====================== Change layer ===============================
(DEFUN CHLayer (/ SSET SSL ENT LAY I OBJ SL)
   (SETQ SSET (SSGET))
   (IF (/= NIL SSET) 
    (PROGN
     (SETQ SSL (SSLENGTH SSET))
     (INITGET "Select Name" 1)
     (SETQ SL (GETKWORD "\nSelect/Name : "))
     (IF (= SL "Select")
         (PROGN
          (SETQ OBJ (ENTSEL))
          (IF (/= OBJ NIL)
              (SETQ LAY (CDR (ASSOC 8 (ENTGET (CAR OBJ)) )) )
          )
         )
     )
     (IF (= SL "Name")
         (PROGN
          (INITGET "" 1)
          (SETQ LAY (GETSTRING "\nLayer name : ") )
         )
     )
   (IF (/= LAY NIL) 
      (PROGN  		
   	(SETQ I 0)
   	(WHILE (< I SSL)
       	  (SETQ ENT (ENTGET (SSNAME SSET I)))
          (SETQ ENT (SUBST (CONS 8 LAY) (ASSOC 8 ENT) ENT))
          (ENTMOD ENT)
          (SETQ I (+ I 1))
        )
      )
     )
    )
   )
   (PRINC)
)
;;;---------------------------------------------------------
(DEFUN CHLayer0 (/ SSET SSL ENT LAY I OBJ SL)
   (SETQ SSET (SSGET))
   (IF (/= NIL SSET) 
    (PROGN
     (SETQ SSL (SSLENGTH SSET))
     (PRINC "Select another object ..." )
     (SETQ OBJ (ENTSEL))
     (IF (/= OBJ NIL)
         (SETQ LAY (CDR (ASSOC 8 (ENTGET (CAR OBJ)) )) )
     )
     (IF (/= LAY NIL) 
      (PROGN  		
   	(SETQ I 0)
   	(WHILE (< I SSL)
       	  (SETQ ENT (ENTGET (SSNAME SSET I)))
          (SETQ ENT (SUBST (CONS 8 LAY) (ASSOC 8 ENT) ENT))
          (ENTMOD ENT)
          (SETQ I (+ I 1))
        )
      )
     )
    )
   )
   (PRINC)
)
;;;---------------------------------------------------------
(DEFUN CHCLayer (/ SSET SSL ENT LAY I )
   (SETQ SSET (SSGET))
   (IF (/= NIL SSET) 
    (PROGN
     (SETQ SSL (SSLENGTH SSET))
     (SETQ LAY (GETVAR "CLAYER") )
     (SETQ I 0)
     (WHILE (< I SSL)
       	  (SETQ ENT (ENTGET (SSNAME SSET I)))
          (SETQ ENT (SUBST (CONS 8 LAY) (ASSOC 8 ENT) ENT))
          (ENTMOD ENT)
          (SETQ I (+ I 1))
     )
    )
   )
   (PRINC)
)
;; ================ 0ff layer ==========================
;;;---------------------------------------------------------
(DEFUN C:LOO (/ SSET SSL ENT LAY I MODE)
   (SETQ SSET (SSGET))
   (IF (/= NIL SSET) 
    (PROGN
     (SETQ SSL (SSLENGTH SSET))
     (SETQ LAY "")
     (SETQ I 0)
     (SETQ MODE 0) 
     (WHILE (< I SSL)
       	  (SETQ ENT (ENTGET (SSNAME SSET I)))
	  (IF (= (CDR (ASSOC '8 ENT)) (GETVAR "CLAYER")) (SETQ MODE 1) )
          (SETQ LAY (STRCAT LAY "," (CDR (ASSOC '8 ENT)) ))
          (SETQ I (+ I 1))
     )
     (COMMAND "LAYER" "OFF" LAY "")
     (IF (= MODE 1) (COMMAND "") )
    )
   )
   (PRINC)
)
;; ================ Set current layer ==========================
;;;---------------------------------------------------------
(DEFUN C:LO (/ OBJ)
     (SETQ OBJ (ENTSEL))
     (IF (/= OBJ NIL)
         (SETVAR "CLAYER" (CDR (ASSOC 8 (ENTGET (CAR OBJ)) )) )
     )
     (PRINC)
)
;;;---------------- Layer 0 --------------------
(DEFUN C:0 (/ LAY)
  (COMMAND "LAYER" "M" "0" "")
  (PRINC)
)
;;;---------------- Layer BAO --------------------
(DEFUN C:BA (/ LAY)
  (COMMAND "LAYER" "M" "BAO" "")
  (PRINC)
)
;;;---------------- Layer CAT --------------------
(DEFUN C:CA (/ LAY)
  (COMMAND "LAYER" "M" "CAT" "")
  (PRINC)
)
;;;---------------- Layer CHI --------------------
(DEFUN C:CH (/ LAY)
  (COMMAND "LAYER" "M" "CHI" "")
  (PRINC)
)
;;;---------------- Layer COT --------------------
(DEFUN C:CO (/ LAY)
  (COMMAND "LAYER" "M" "COT" "")
  (PRINC)
)
;;;---------------- Layer DAM --------------------
(DEFUN C:DA (/ LAY)
  (COMMAND "LAYER" "M" "DAM" "")
  (PRINC)
)
;;;---------------- Layer DIM --------------------
(DEFUN C:DI (/ LAY)
  (COMMAND "LAYER" "M" "DIM" "")
  (PRINC)
)
;;;---------------- Layer KHUAT --------------------
(DEFUN C:KH (/ LAY)
  (COMMAND "LAYER" "M" "KHUAT" "")
  (PRINC)
)
;;;---------------- Layer SYMBOL --------------------
(DEFUN C:SY (/ LAY)
  (COMMAND "LAYER" "M" "SYMBOL" "")
  (PRINC)
)
;;;---------------- Layer TEXT --------------------
(DEFUN C:TE (/ LAY)
  (COMMAND "LAYER" "M" "TEXT" "")
  (PRINC)
)
;;;---------------- Layer THEP --------------------
(DEFUN C:TH (/ LAY)
  (COMMAND "LAYER" "M" "THEP" "")
  (PRINC)
)
;;;---------------- Layer TRUC --------------------
(DEFUN C:Tu (/ LAY)
  (COMMAND "LAYER" "M" "TRUC" "")
  (PRINC)
)
;;;---------------- Layer XANH --------------------
(DEFUN C:XA (/ LAY)
  (COMMAND "LAYER" "M" "XANH" "")
  (PRINC)
)
;; ======================================================================
(defun c:LL () (CHLayer))
(defun c:SS () (CHLayer0))
(defun c:CS () (CHCLayer))
(defun c:LCL ()
 (princ "\nLayer command list : LL,SS,CS; LO,LOO;") 
 (princ "\n                     0,BA,CA,CH,CO,DA,DI,KH,SY,TE,TH,TR,XA")
 (princ)
)
;; ======================================================================
;(PRINC "\nLAYER loaded. Type LCL to see command list.")
(PRINC)
