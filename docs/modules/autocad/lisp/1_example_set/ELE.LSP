(DEFUN C:eLe()
(setq ent (ssget '((0 . "point"))))
(setq num (sslength ent))
(SETQ CNT 0)
(setq hi (getreal"\nEnter Text Hight:"))
(setq ed (* -1 hi))
(REPEAT NUM
(setq s1 (ssname ent cnt))
(setq s2 (entget s1))
(setq pt (cdr (assoc 10 s2)))
(SETQ CNT (1+ CNT))
(SETQ Z (CADDR PT))
(SETQ X (CAR PT))
(SETQ Y (CADR PT))
(SETQ FB (FIX Z))
(SETQ TE1 (* Z 1000))
(SETQ TE2 (* FB 1000))
(SETQ TE3 (- TE1 TE2))
(IF (>= TE3 995)
        (PROGN
        (SETQ TE4 (/ TE3 1000))
        (SETQ Z (+ 1 (- Z TE4)))
            )
        )
(SETQ FK (FIX Z))
(SETQ FZ (RTOS FK 2 0))
(SETQ sZ (RTOS Z 2 2))
(setq a1 (strlen fz))
(setq a2 (+ a1 2))
(setq rz (substr sz a2 2))
(setq fel (strcat fz " " rz ""))
(setq hhi (/ hi 2))
(setq fpt (polar pt 1.57 hhi))
(COMMAND "TEXT" "M" fPt hi 0 fel)
(command "filedia" "1")
)
(princ)
)
