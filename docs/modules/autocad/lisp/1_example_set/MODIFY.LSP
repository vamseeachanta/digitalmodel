(DEFUN C:LP(/ MOj MO@ MOQ MOl)(PRINC"\nSelect lines :")(SETQ MOj(SSGET))(IF(/= NIL MOj)(PROGN(SETQ MOQ(SSLENGTH MOj))(INITGET 4)(SETQ MO@(GETREAL"New width : "))(IF(/= NIL MO@)(WHILE(> MOQ 0)(SETQ MOl(SSNAME MOj(SETQ MOQ(- MOQ 1))))(IF(=(CDR(ASSOC(quote 0)(ENTGET MOl)))"LINE")(COMMAND"PEDIT"MOl"Y""W"MO@""))))))(PRINC))(DEFUN C:PW(/ MOj MOQ MOl MO& MO1)(PRINC"\nSelect polylines :")(SETQ MOj(SSGET))(IF(/= NIL MOj)(PROGN(SETQ MOQ(SSLENGTH MOj))(INITGET 4"")(SETQ MO&(GETREAL"\nNew width : "))(IF(/= MO& NIL)(PROGN(SETQ MO1 0)(WHILE(< MO1 MOQ)(SETQ MOl(ENTGET(SSNAME MOj MO1)))(IF(=(CDR(ASSOC(quote 0)MOl))"POLYLINE")(PROGN(SETQ MOl(SUBST(CONS 40 MO&)(ASSOC 40 MOl)MOl))(SETQ MOl(SUBST(CONS 41 MO&)(ASSOC 41 MOl)MOl))(ENTMOD MOl)))(SETQ MO1(+ MO1 1)))))))(PRINC))(DEFUN C:PLL(/ MOj MOQ MOl MO# MO1)(PRINC"\nSelect polylines :")(SETQ MOj(SSGET))(IF(/= NIL MOj)(PROGN(SETQ MOQ(SSLENGTH MOj))(SETQ MO#(GETSTRING"\nNew layer : "))(IF(/= MO# NIL)(PROGN(SETQ MO1 0)(WHILE(< MO1 MOQ)(SETQ MOl(ENTGET(SSNAME MOj MO1)))(IF(=(CDR(ASSOC(quote 0)MOl))"POLYLINE")(PROGN(SETQ MOl(SUBST(CONS 8 MO#)(ASSOC 8 MOl)MOl))(ENTMOD MOl)))(SETQ MO1(+ MO1 1)))))))(PRINC))(DEFUN C:CR(/ MOj MOQ MOl MO0 MO1)(PRINC"\nSelect circles :")(SETQ MOj(SSGET))(IF(/= NIL MOj)(PROGN(SETQ MOQ(SSLENGTH MOj))(INITGET 4"")(SETQ MO0(GETREAL"\nNew radius : "))(IF(/= MO0 NIL)(PROGN(SETQ MO1 0)(WHILE(< MO1 MOQ)(SETQ MOl(ENTGET(SSNAME MOj MO1)))(IF(=(CDR(ASSOC(quote 0)MOl))"CIRCLE")(PROGN(SETQ MOl(SUBST(CONS 40 MO0)(ASSOC 40 MOl)MOl))(ENTMOD MOl)))(SETQ MO1(+ MO1 1)))))))(PRINC))(DEFUN C:CL(/ MOj MOQ MOl MO# MO1)(PRINC"\nSelect circles :")(SETQ MOj(SSGET))(IF(/= NIL MOj)(PROGN(SETQ MOQ(SSLENGTH MOj))(SETQ MO#(GETSTRING"\nNew layer : "))(IF(/= MO# NIL)(PROGN(SETQ MO1 0)(WHILE(< MO1 MOQ)(SETQ MOl(ENTGET(SSNAME MOj MO1)))(IF(=(CDR(ASSOC(quote 0)MOl))"CIRCLE")(PROGN(SETQ MOl(SUBST(CONS 8 MO#)(ASSOC 8 MOl)MOl))(ENTMOD MOl)))(SETQ MO1(+ MO1 1)))))))(PRINC))(DEFUN C:TL(/ MOj MOQ MOl MO# MO1)(PRINC"\nSelect texts :")(SETQ MOj(SSGET))(IF(/= NIL MOj)(PROGN(SETQ MOQ(SSLENGTH MOj))(SETQ MO#(GETSTRING"\nNew layer : "))(IF(/= MO# NIL)(PROGN(SETQ MO1 0)(WHILE(< MO1 MOQ)(SETQ MOl(ENTGET(SSNAME MOj MO1)))(IF(=(CDR(ASSOC(quote 0)MOl))"TEXT")(PROGN(SETQ MOl(SUBST(CONS 8 MO#)(ASSOC 8 MOl)MOl))(ENTMOD MOl)))(SETQ MO1(+ MO1 1)))))))(PRINC))(DEFUN C:DL(/ MOj MOQ MOl MO# MO1)(PRINC"\nSelect dimensions :")(SETQ MOj(SSGET))(IF(/= NIL MOj)(PROGN(SETQ MOQ(SSLENGTH MOj))(SETQ MO#(GETSTRING"\nNew layer : "))(IF(/= MO# NIL)(PROGN(SETQ MO1 0)(WHILE(< MO1 MOQ)(SETQ MOl(ENTGET(SSNAME MOj MO1)))(IF(=(CDR(ASSOC(quote 0)MOl))"DIMENSION")(PROGN(SETQ MOl(SUBST(CONS 8 MO#)(ASSOC 8 MOl)MOl))(ENTMOD MOl)))(SETQ MO1(+ MO1 1)))))))(PRINC))(DEFUN C:MCL()(PRINC"\nModify command list : LP; PW,PLL; CR,CL; TL; DL")(PRINC))(DEFUN C:ENT(/ MO$ MOO)(SETQ MO$(MO|))(SETQ ENAME(CAR MO$))(SETQ MOO(ENTGET ENAME(LIST"*")))(PRINC MOO)(PRINC))(PRINC)
