(defun C:Ct ()
(setq v (getvar "osmode"))
(setq pt1 (getpoint "Diem dau : "))
(setq pt2 (getpoint "Diem cuoi : " pt1))
(command "osnap" "none")
(setq goc (angle pt1 pt2))
(setq kcach (distance pt1 pt2))
(setq pt3 (polar pt1 goc (* 2 (/ kcach 5))))
(setq pt4 (polar pt1 goc (* 3 (/ kcach 5))))
(setq pt5 (polar pt3 (+ (/ PI 2) goc) (* kcach 0.15)))
(setq pt6 (polar pt4 (+ (/ PI 2) goc) (* kcach -0.15)))
(command "pline" pt1 pt3 pt5 pt6 pt4 pt2 "")
(setvar "osmode" v )
)
