(defun C:CE ()
  (setvar "cmdecho" 0)
  (setq INDEX 0
    G1 (ssget)
    SG1 (sslength G1)
  )
  (if (= El nil)
    (setq El 0)
  )
  (if (= NELV nil)
    (setq NELV 0)
  )
  (setq A NELV)
  (princ "\nEnter desired elevation: default <")
  (princ NELV)
  (princ "> ")
  (setq NELV (getreal))
  (if (= NELV nil)
    (setq NELV A)
  )
  (repeat SG1
    (setq E (ssname G1 index))
    (setq E1  (entget (ssname G1 index)))
    (setq El (car (cdr (cdr (cdr (assoc 10 E1))))))
    (setq DIFF (- NELV EL))
    (setq TXELV (strcat "@0,0," (rtos DIFF 2 4)))
    (command "move" E "" "0,0,0" TXELV)
    (setq INDEX (+ INDEX 1))
  )
  (setvar "cmdecho" 1)
  (princ)
) ; end chelev.lsp
