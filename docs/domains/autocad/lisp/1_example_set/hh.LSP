******************************************************************************
;*************************************************************************** *
;*                                                                         * * 
;* NAME     :        TRIM DIMENSION                                        * *
;*                                                                         * * 
;* FUNCTION :        ALLOWS TOU TO REVISE POSITION OF DIMENSION EXTENSION  * *
;*                   "DEFINING POINT" ALONG ITS "X" AXIS                   * *
;*                                                                         * *
;* WRITTEN  :        NGUYEN HAI NAM ACT (VIETNAM)                          * *
;*                   1-1-2000                                              * *
;*                                                                         * *
;*************************************************************************** * 
******************************************************************************
(DEFUN C:DY ()
 (SETQ CMD (GETVAR "CMDECHO"))
 (SETVAR "CMDECHO" 0)
 (COMMAND "UCS" "W")
 (SETVAR "CMDECHO" 1)
 (PROMPT"\nSelect vertical dimension(s) extensions to be aligned")
 (SETQ SET (SSGET))
 (PROMPT"\nSelect new extension position")
 (SETQ P1 (GETPOINT))
 (SETQ X3 (CAR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L13 (ASSOC 13 A))
     (SETQ M13 (CDR L13))
     (SETQ L14 (ASSOC 14 A))
     (SETQ M14 (CDR L14))
     (SETQ P13 (LIST 13 X3 (CADR M13) (CADDR M13)))
     (SETQ P14 (LIST 14 X3 (CADR M14) (CADDR M14)))
     (SETQ A (SUBST P13 L13 A))
     (SETQ A (SUBST P14 L14 A))
     (ENTMOD A)			
    )
   )
  (SETQ INDEX (+ INDEX 1))
 )
 (SETVAR "CMDECHO" 0)
 (COMMAND "UCS" "P")
 (SETVAR "CMDECHO" CMD)
 (PRINC)
)
*************************************
(DEFUN C:DX ()
 (SETQ CMD (GETVAR "CMDECHO"))
 (SETVAR "CMDECHO" 0)
 (COMMAND "UCS" "W")
 (SETVAR "CMDECHO" 1)
 (PROMPT"\nSelect dimension(s) to be aligned")
 (SETQ SET (SSGET))
 (PROMPT"\nSelect new dimension position")
 (SETQ P1 (GETPOINT))
 (SETQ Y3 (CADR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L13 (ASSOC 13 A))
     (SETQ M13 (CDR L13))
     (SETQ L14 (ASSOC 14 A))
     (SETQ M14 (CDR L14))
     (SETQ P13 (LIST 13 (CAR M13) Y3 (CADDR M13)))
     (SETQ T13 (CDR P13))
     (SETQ P14 (LIST 14 (CAR M14) Y3 (CADDR M14)))
     (SETQ A (SUBST P13 L13 A))
     (SETQ A (SUBST P14 L14 A))
     (ENTMOD A)			
    )
   )
  (SETQ INDEX (+ INDEX 1))
 )
 (SETVAR "CMDECHO" 0)
 (COMMAND "UCS" "P")
 (SETVAR "CMDECHO" CMD)
)
******************************************************
;*************************************************************************
;*                                                                       *
;* NAME     :        X,Y-ALDIM.LSP                                       *
;*                                                                       *
;* FUNCTION :        ALLOWS GROUPS OF DIMENSIONS TO BE ALIGNED ALONG A   *
;*                   COMMON "X" AXIS.                                    *
;*                                                                       *
;* WRITTEN  :       NGUYEN HAI NAM  (VIET NAM)                           *
;*                   1-1-2000                                            *
;*                                                                       *
;*************************************************************************
(DEFUN C:YD ()
 (SETQ CMD (GETVAR "CMDECHO"))
 (SETVAR "CMDECHO" 0)
 (COMMAND "UCS" "W")
 (SETVAR "CMDECHO" 1)
 (PROMPT"\nSelect dimension(s) to be aligned")
 (SETQ SET (SSGET))
 (PROMPT"\nSelect new dimension position")
 (SETQ P1 (GETPOINT))
 (SETQ X3 (CAR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L10 (ASSOC 10 A))
     (SETQ M10 (CDR L10))
     (SETQ L11 (ASSOC 11 A))
     (SETQ M11 (CDR L11))
     (SETQ P10 (LIST 10 X3 (CADR M10) (CADDR M10)))
     (SETQ A (SUBST P10 L10 A))
     (ENTMOD A)			
    )
   )
  (SETQ INDEX (+ INDEX 1))
 )
 (SETVAR "CMDECHO" 0)
 (COMMAND "UCS" "P")
 (SETVAR "CMDECHO" CMD)
)

************************************
(DEFUN C:XD ()
 (SETQ CMD (GETVAR "CMDECHO"))
 (SETVAR "CMDECHO" 0)
 (COMMAND "UCS" "W")
 (SETVAR "CMDECHO" 1)
 (PROMPT"\nSelect dimension(s) to be aligned")
 (SETQ SET (SSGET))
 (PROMPT"\nSelect new dimension position")
 (SETQ P1 (GETPOINT))
 (SETQ Y3 (CADR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L10 (ASSOC 10 A))
     (SETQ M10 (CDR L10))
     (SETQ P10 (LIST 10 (CAR M10) Y3 (CADDR M10)))
     (SETQ A (SUBST P10 L10 A))
     (ENTMOD A)			
    )
   )
  (SETQ INDEX (+ INDEX 1))
 )
 (SETVAR "CMDECHO" 0)
 (COMMAND "UCS" "P")
 (SETVAR "CMDECHO" CMD)
)


************************************************************
(DEFUN INIT  ()
  (setq	Blm    (getvar "BLIPMODE")
	Cmd    (getvar "CMDECHO")
	Os     (getvar "OSMODE")
	Olderr *ERROR*
	)				;setq       
  (setvar "BLIPMODE" 0)
  (setvar "CMDECHO" 0)
  (defun *ERROR*  (Msg)
    (princ "\n:")
    (Princ Msg)
    (setvar "blipmode" Blm)
    (setvar "CMDECHO" Cmd)
    (setvar "OSMODE" Os)
    (setq *ERROR* Olderr)
    (princ)
    ))					;init
(DEFUN REINIT  ()
  (setvar "blipmode" Blm)
  (setvar "CMDECHO" Cmd)
  (setvar "OSMODE" Os)
  (setq *ERROR* Olderr)
  (princ)
  )					;reinit
(defun c:nh  (/ name1 ent A b sget)
  (init)
  (setq	name1 (car (entsel))
	sget  (ssget)
	ent   (cdr (assoc 0 (setq A (entget name1))))
	)
  (if
    (or	(= "LINE" ent)
	(= "ARC" ent))
	(command "pedit" name1 "y" "j" sget "" "")
	(command "pedit" name1 "j" sget "" ""))
  (reinit)
  (princ)
 )
****************************************************
(defun c:NC ()
  (command "sh" "nc")
)
(defun c:ZX ()
  (command "ZOOM" "p")
)
(defun c:MP ()
  (command "move" "p" "")
)
(defun c:ZD ()
  (command "ZOOM" "D")
)
(defun c:ZE ()
  (command "zoom" "E")
)
(defun c:- ()
  (command "zoom" "0.5x")
)
(defun c:= ()
  (command "zoom" "2.0x")
)
(defun c:AS ()
  (command "AREA" "O")
)
(defun c:V ()
  (command "zoom" "0.5x")
)
(defun c:GG ()
  (command "zoom" "2.0x")
)
(defun c:ZZ ()
  (command "zoom" "")
)
(defun c:EE ()
  (ssget)
  (command "extend" "p" "" "f")
)
(defun c:CC ()
  (ssget)
  (command "copy" "p" "" "M")
)
(defun c:CV ()
  (command "copy" "p" "")
)
(defun c:ff ()
  (command "fillet" "r" "0")
)
(defun c:fc ()
  (command "fillet" "c")
)
(defun c:S ()
  (command "stretch" "C")
)
(defun c:OI ()
  (command "offset" "t")
)
(defun c:OO ()
  (command "offset" "")
)
*********************************
(defun c:U3 ()
  (command "UCS" "3p")
)
(defun c:Ui ()
  (command "UCS" "e")
)
(defun c:UE ()
  (command "UCS" "e")
)
(defun c:UY ()
  (command "UCS" "w" "")
)
*******************************
(defun c:Ci3 ()
  (command "circle" "3p" "")
)
(defun c:Ci2 ()
  (command "circle" "2p" "")
)
(defun c:CT ()
  (command "circle" "ttr" "")
)
*********************************
(defun c:0` ()
  (command "color" "bylayer")
)
(defun c:0- ()
  (command "color" "bylayer")
)
(defun c:1` ()
  (command "color" "1")
)
(defun c:2` ()
  (command "color" "2")
)
(defun c:3` ()
  (command "color" "3")
)
(defun c:4` ()
  (command "color" "4")
)
(defun c:5` ()  
  (command "color" "5")
)
(defun c:6` ()
  (command "color" "6")
)
(defun c:7` ()
  (command "color" "7")
)
(defun c:8` ()
  (command "color" "8")
)
(defun c:9` ()
  (command "color" "9")
)
(defun c:10` ()
  (command "color" "10")
)
*******************************************
(defun c:c1 ()
  (ssget)
  (command "change" "p" "" "p" "c" "1" "")
)
(defun c:c2 ()
  (ssget)
  (command "change" "p" "" "p" "c" "2" "")
)
(defun c:c3 ()
  (ssget)
  (command "change" "p" "" "p" "c" "3" "")
)
(defun c:c4 ()
  (ssget)
  (command "change" "p" "" "p" "c" "4" "")
)
(defun c:c5 ()
  (ssget)
  (command "change" "p" "" "p" "c" "5" "")
)
(defun c:c6 ()
  (ssget)
  (command "change" "p" "" "p" "c" "6" "")
)
(defun c:c7 ()
  (ssget)
  (command "change" "p" "" "p" "c" "7" "")
)
(defun c:c8 ()
  (ssget)
  (command "change" "p" "" "p" "c" "8" "")
)
(defun c:c9 ()
  (ssget)
  (command "change" "p" "" "p" "c" "9" "")
)
(defun c:c0 ()
  (ssget)
  (command "change" "p" "" "p" "c" "bylayer" "")
)  
(defun c:k ()
  (ssget)
  (command "change" "p" "" "p" "c" "bylayer" "")
)  
(defun c:32 ()
  (ssget)
  (command "change" "p" "" "p" "c" "32" "")
)
(defun c:43 ()
  (ssget)
  (command "change" "p" "" "p" "c" "43" "")
)
(defun c:53 ()
  (ssget)
  (command "change" "p" "" "p" "c" "53" "")
)
(defun c:74 ()
  (ssget)
  (command "change" "p" "" "p" "c" "74" "")
)

**************************************************

(defun c:r3 () (ssget) (command "rotate" "p" "" pause "30"))
(defun c:r-3 () (ssget) (command "rotate" "p" "" pause "-30"))
(defun c:r4 () (ssget) (command "rotate" "p" "" pause "45"))
(defun c:r6 () (ssget) (command "rotate" "p" "" pause "60"))
(defun c:r-6 () (ssget) (command "rotate" "p" "" pause "-60"))
(defun c:r9 () (ssget) (command "rotate" "p" "" pause "90"))
(defun c:r18 () (ssget) (command "rotate" "p" "" pause "180"))
(defun c:r-4 () (ssget) (command "rotate" "p" "" pause "-45"))
(defun c:-9 () (ssget) (command "rotate" "p" "" pause "-90"))
(defun c:r4 () (ssget) (command "rotate" "p" "" pause "180"))

*********************************
(defun c:m1 ()
  (command "mline" "s" "110")
)
(defun c:m2 ()
  (command "mline" "s" "220")
)
(defun c:m5 ()
  (command "mline" "s" "50")
)
(defun c:m6 ()
  (command "mline" "s" "60")
)
(defun c:m7 ()
  (command "mline" "s" "700")
)
(defun c:m92 ()
  (command "mline" "s" "920")
)
*******************************
(defun c:D1 ()
  (command "donut" "0" "10")
)
(defun c:D2 ()
  (command "donut" "0" "20")
)
(defun c:D3 ()
  (command "donut" "0" "30")
)
(defun c:D4 ()
  (command "donut" "0" "40")
)
(defun c:D5 ()
  (command "donut" "0" "50")
)
(defun c:D6 ()
  (command "donut" "0" "60")
)
(defun c:D7 ()
  (command "donut" "0" "70")
)
(defun c:D8 ()
  (command "donut" "0" "90")
)
(defun c:D9 ()
  (command "donut" "0" "90")
)
(defun c:D10 ()
  (command "donut" "0" "100")
)
(defun c:D11 ()
  (command "donut" "0" "110")
)
(defun c:D12 ()
  (command "donut" "0" "120")
)
(defun c:D13 ()
  (command "donut" "0" "130")
)
(defun c:D14 ()
  (command "donut" "0" "140")
)
(defun c:D15 ()
  (command "donut" "0" "150")
)
(defun c:D16 ()
  (command "donut" "0" "160")
)
(defun c:D17 ()
  (command "donut" "0" "170")
)
(defun c:D18 ()
  (command "donut" "0" "180")
)
(defun c:D19 ()
  (command "donut" "0" "190")
)
(defun c:D20 ()
  (command "donut" "0" "200")
)
(defun c:D21 ()
  (command "donut" "0" "210")
)
(defun c:D22 ()
  (command "donut" "0" "220")
)
(defun c:D23 ()
  (command "donut" "0" "230")
)
(defun c:D24 ()
  (command "donut" "0" "240")
)
(defun c:D25 ()
  (command "donut" "0" "250")
)
(defun c:D26 ()
  (command "donut" "0" "270")
)
(defun c:D28 ()
  (command "donut" "0" "280")
)
(defun c:D29 ()
  (command "donut" "0" "290")
)
(defun c:D30 ()
  (command "donut" "0" "300")
)

**************************************************
(defun c:ff ()
  (command "fillet" "r" "0")
)
(defun c:fc ()
  (command "fillet" "c")
)
(defun c:f1 () 
  (command "fillet" "r" "10")
)
(defun c:f2 () 
  (command "fillet" "r" "20")
)
(defun c:f3 () 
  (command "fillet" "r" "30")
)
(defun c:f4 () 
  (command "fillet" "r" "40")
)
(defun c:f5 () 
  (command "fillet" "r" "50")
)
(defun c:f6 () 
  (command "fillet" "r" "60")
)
(defun c:f7 () 
  (command "fillet" "r" "70")
)
(defun c:f8 () 
  (command "fillet" "r" "80")
)
(defun c:f9 () 
  (command "fillet" "r" "90")
)
(defun c:f10 () 
  (command "fillet" "r" "100")
)
(defun c:f11 () 
  (command "fillet" "r" "110")
)
(defun c:f12 () 
  (command "fillet" "r" "120")
)
(defun c:f13 () 
  (command "fillet" "r" "130")
)
(defun c:f14 () 
  (command "fillet" "r" "140")
)
(defun c:f15 () 
  (command "fillet" "r" "150")
)
(defun c:f16 () 
  (command "fillet" "r" "160")
)
(defun c:f17 () 
  (command "fillet" "r" "170")
)
(defun c:f18 () 
  (command "fillet" "r" "180")
)
(defun c:f19 () 
  (command "fillet" "r" "190")
)
(defun c:f20 () 
  (command "fillet" "r" "200")
)
(defun c:f21 () 
  (command "fillet" "r" "210")
)
(defun c:f22 () 
  (command "fillet" "r" "220")
)
(defun c:f23 () 
  (command "fillet" "r" "230")
)
(defun c:f24 () 
  (command "fillet" "r" "240")
)
(defun c:f25 () 
  (command "fillet" "r" "250")
)
(defun c:f26 () 
  (command "fillet" "r" "260")
)
(defun c:f27 () 
  (command "fillet" "r" "270")
)
(defun c:f28 () 
  (command "fillet" "r" "280")
)
(defun c:f29 () 
  (command "fillet" "r" "290")
)
(defun c:f30 () 
  (command "fillet" "r" "300")
)
(defun c:f31 () 
  (command "fillet" "r" "310")
)
(defun c:f32 () 
  (command "fillet" "r" "320")
)
(defun c:f33 () 
  (command "fillet" "r" "330")
)
(defun c:f34 () 
  (command "fillet" "r" "340")
)
(defun c:f35 () 
  (command "fillet" "r" "350")
)
(defun c:f36 () 
  (command "fillet" "r" "360")
)
(defun c:f37 () 
  (command "fillet" "r" "370")
)
(defun c:f38 () 
  (command "fillet" "r" "380")
)
(defun c:f39 () 
  (command "fillet" "r" "390")
)
(defun c:f40 () 
  (command "fillet" "r" "400")
)
(defun c:f41 () 
  (command "fillet" "r" "410")
)
(defun c:f42 () 
  (command "fillet" "r" "420")
)
(defun c:f43 () 
  (command "fillet" "r" "430")
)
(defun c:f44 () 
  (command "fillet" "r" "440")
)
(defun c:f45 () 
  (command "fillet" "r" "450")
)
(defun c:f46 () 
  (command "fillet" "r" "460")
)
(defun c:f47 () 
  (command "fillet" "r" "470")
)
(defun c:f48 () 
  (command "fillet" "r" "480")
)
(defun c:f49 () 
  (command "fillet" "r" "490")
)
(defun c:f50 () 
  (command "fillet" "r" "500")
)
(defun c:f51 () 
  (command "fillet" "r" "510")
)
(defun c:f52 () 
  (command "fillet" "r" "520")
)
(defun c:f53 () 
  (command "fillet" "r" "530")
)
(defun c:f54 () 
  (command "fillet" "r" "540")
)
(defun c:f55 () 
  (command "fillet" "r" "550")
)
(defun c:f56 () 
  (command "fillet" "r" "560")
)
(defun c:f57 () 
  (command "fillet" "r" "570")
)
(defun c:f58 () 
  (command "fillet" "r" "580")
)
(defun c:f59 () 
  (command "fillet" "r" "590")
)
(defun c:f60 () 
  (command "fillet" "r" "600")
)
(defun c:f61 () 
  (command "fillet" "r" "610")
)
(defun c:f62 () 
  (command "fillet" "r" "620")
)
(defun c:f63 () 
  (command "fillet" "r" "630")
)
(defun c:f64 () 
  (command "fillet" "r" "640")
)
(defun c:f65 () 
  (command "fillet" "r" "650")
)
(defun c:f66 () 
  (command "fillet" "r" "660")
)
(defun c:f67 () 
  (command "fillet" "r" "670")
)
(defun c:f68 () 
  (command "fillet" "r" "680")
)
(defun c:f69 () 
  (command "fillet" "r" "690")
)
(defun c:f70 () 
  (command "fillet" "r" "700")
)
(defun c:f71 () 
  (command "fillet" "r" "710")
)
(defun c:f72 () 
  (command "fillet" "r" "720")
)
(defun c:f73 () 
  (command "fillet" "r" "730")
)
(defun c:f74 () 
  (command "fillet" "r" "740")
)
(defun c:f75 () 
  (command "fillet" "r" "750")
)
(defun c:f76 () 
  (command "fillet" "r" "760")
)
(defun c:f77 () 
  (command "fillet" "r" "770")
)
(defun c:f78 () 
  (command "fillet" "r" "780")
)
(defun c:f79 () 
  (command "fillet" "r" "790")
)
(defun c:f80 () 
  (command "fillet" "r" "800")
)
(defun c:f81 () 
  (command "fillet" "r" "810")
)
(defun c:f82 () 
  (command "fillet" "r" "820")
)
(defun c:f83 () 
  (command "fillet" "r" "830")
)
(defun c:f84 () 
  (command "fillet" "r" "840")
)
(defun c:f85 () 
  (command "fillet" "r" "850")
)
(defun c:f86 () 
  (command "fillet" "r" "860")
)
(defun c:f87 () 
  (command "fillet" "r" "870")
)
(defun c:f88 () 
  (command "fillet" "r" "880")
)
(defun c:f89 () 
  (command "fillet" "r" "890")
)
(defun c:f90 () 
  (command "fillet" "r" "900")
)
(defun c:f91 () 
  (command "fillet" "r" "910")
)
(defun c:f92 () 
  (command "fillet" "r" "920")
)
(defun c:f93 () 
  (command "fillet" "r" "940")
)
(defun c:f95 () 
  (command "fillet" "r" "950")
)
(defun c:f96 () 
  (command "fillet" "r" "960")
)
(defun c:f97 () 
  (command "fillet" "r" "970")
)
(defun c:f98 () 
  (command "fillet" "r" "980")
)
(defun c:f99 () 
  (command "fillet" "r" "990")
)
(defun c:f100 () 
  (command "fillet" "r" "1000")
)
(defun c:f115 () 
  (command "fillet" "r" "1150")
)
(defun c:f120 () 
  (command "fillet" "r" "1200")
)
(defun c:f125 () 
  (command "fillet" "r" "1250")
)
(defun c:f130 () 
  (command "fillet" "r" "1300")
)
(defun c:f135 () 
  (command "fillet" "r" "1350")
)
(defun c:f140 () 
  (command "fillet" "r" "1400")
)
(defun c:f145 () 
  (command "fillet" "r" "1450")
)
(defun c:f150 () 
  (command "fillet" "r" "1500")
)
(defun c:f155 () 
  (command "fillet" "r" "1550")
)
(defun c:f160 () 
  (command "fillet" "r" "1600")
)
(defun c:f165 () 
  (command "fillet" "r" "1650")
)
(defun c:f170 () 
  (command "fillet" "r" "1700")
)
(defun c:f175 () 
  (command "fillet" "r" "1750")
)
(defun c:f180 () 
  (command "fillet" "r" "1800")
)
(defun c:f185 () 
  (command "fillet" "r" "1850")
)
(defun c:f190 () 
  (command "fillet" "r" "1900")
)
(defun c:f195 () 
  (command "fillet" "r" "1950")
)
(defun c:f200 () 
  (command "fillet" "r" "2000")
)


******************************************
(defun c:10 ()
  (command "offset" "10")
)
(defun c:15 ()
  (command "offset" "15")
)
(defun c:20 ()
  (command "offset" "20")
)
(defun c:25 ()
  (command "offset" "25")
)
(defun c:35 ()
  (command "offset" "35")
)
(defun c:45 ()
  (command "offset" "45")
)
(defun c:50 ()
  (command "offset" "50")
)
(defun c:55 ()
  (command "offset" "55")
)
(defun c:60 ()
  (command "offset" "60")
)
(defun c:65 ()
  (command "offset" "65")
)
(defun c:70 ()
  (command "offset" "70")
)
(defun c:75 ()
  (command "offset" "75")
)
(defun c:80 ()
  (command "offset" "80")
)
(defun c:85 ()
  (command "offset" "85")
)
(defun c:90 ()
  (command "offset" "90")
)
(defun c:95 ()
  (command "offset" "95")
)
(defun c:100 ()
  (command "offset" "100")
)
(defun c:110 ()
  (command "offset" "110")
)
(defun c:120 ()
  (command "offset" "120")
)
(defun c:130 ()
  (command "offset" "130")
)
(defun c:140 ()
  (command "offset" "140")
)
(defun c:150 ()
  (command "offset" "150")
)
(defun c:160 ()
  (command "offset" "160")
)
(defun c:170 ()
  (command "offset" "170")
)
(defun c:180 ()
  (command "offset" "180")
)
(defun c:190 ()
  (command "offset" "190")
)
(defun c:200 ()
  (command "offset" "200")
)
(defun c:210 ()
  (command "offset" "210")
)
(defun c:220 ()
  (command "offset" "220")
)
(defun c:230 ()
  (command "offset" "230")
)
(defun c:240 ()
  (command "offset" "240")
)
(defun c:250 ()
  (command "offset" "250")
)
(defun c:260 ()
  (command "offset" "260")
)
(defun c:270 ()
  (command "offset" "270")
)
(defun c:280 ()
  (command "offset" "280")
)
(defun c:290 ()
  (command "offset" "290")
)
(defun c:300 ()
  (command "offset" "300")
)
(defun c:310 ()
  (command "offset" "310")
)
(defun c:320 ()
  (command "offset" "320")
)
(defun c:330 ()
  (command "offset" "330")
)
(defun c:340 ()
  (command "offset" "340")
)
(defun c:350 ()
  (command "offset" "350")
)
(defun c:360 ()
  (command "offset" "360")
)
(defun c:370 ()
  (command "offset" "370")
)
(defun c:380 ()
  (command "offset" "380")
)
(defun c:390 ()
  (command "offset" "390")
)
(defun c:400 ()
  (command "offset" "400")
)
(defun c:410 ()
  (command "offset" "410")
)
(defun c:420 ()
  (command "offset" "420")
)
(defun c:430 ()
  (command "offset" "430")
)
(defun c:440 ()
  (command "offset" "440")
)
(defun c:450 ()
  (command "offset" "450")
)
(defun c:460 ()
  (command "offset" "460")
)
(defun c:470 ()
  (command "offset" "470")
)
(defun c:480 ()
  (command "offset" "480")
)
(defun c:490 ()
  (command "offset" "490")
)
(defun c:500 ()
  (command "offset" "500")
)
(defun c:510 ()
  (command "offset" "510")
)
(defun c:520 ()
  (command "offset" "520")
)
(defun c:530 ()
  (command "offset" "530")
)
(defun c:540 ()
  (command "offset" "540")
)
(defun c:550 ()
  (command "offset" "550")
)
(defun c:560 ()
  (command "offset" "560")
)
(defun c:570 ()
  (command "offset" "570")
)
(defun c:580 ()
  (command "offset" "580")
)
(defun c:590 ()
  (command "offset" "590")
)
(defun c:600 ()
  (command "offset" "600")
)
(defun c:610 ()
  (command "offset" "610")
)
(defun c:620 ()
  (command "offset" "620")
)
(defun c:630 ()
  (command "offset" "630")
)
(defun c:640 ()
  (command "offset" "640")
)
(defun c:650 ()
  (command "offset" "650")
)
(defun c:660 ()
  (command "offset" "660")
)
(defun c:670 ()
  (command "offset" "670")
)
(defun c:680 ()
  (command "offset" "680")
)
(defun c:690 ()
  (command "offset" "690")
)
(defun c:700 ()
  (command "offset" "700")
)
(defun c:710 ()
  (command "offset" "710")
)
(defun c:720 ()
  (command "offset" "720")
)
(defun c:730 ()
  (command "offset" "730")
)
(defun c:740 ()
  (command "offset" "740")
)
(defun c:750 ()
  (command "offset" "750")
)
(defun c:760 ()
  (command "offset" "760")
)
(defun c:770 ()
  (command "offset" "770")
)
(defun c:780 ()
  (command "offset" "780")
)
(defun c:790 ()
  (command "offset" "790")
)
(defun c:800 ()
  (command "offset" "800")
)
(defun c:810 ()
  (command "offset" "810")
)
(defun c:820 ()
  (command "offset" "820")
)
(defun c:830 ()
  (command "offset" "830")
)
(defun c:840 ()
  (command "offset" "840")
)
(defun c:850 ()
  (command "offset" "850")
)
(defun c:860 ()
  (command "offset" "860")
)
(defun c:870 ()
  (command "offset" "870")
)
(defun c:880 ()
  (command "offset" "880")
)
(defun c:890 ()
  (command "offset" "890")
)
(defun c:900 ()
  (command "offset" "900")
)
(defun c:910 ()
  (command "offset" "910")
)
(defun c:920 ()
  (command "offset" "920")
)
(defun c:930 ()
  (command "offset" "930")
)
(defun c:940 ()
  (command "offset" "940")
)
(defun c:950 ()
  (command "offset" "950")
)
(defun c:960 ()
  (command "offset" "960")
)
(defun c:970 ()
  (command "offset" "970")
)
(defun c:980 ()
  (command "offset" "980")
)
(defun c:990 ()
  (command "offset" "990")
)
(defun c:1000 ()
  (command "offset" "1000")
)
(defun c:1100 ()
  (command "offset" "1100")
)
(defun c:1150 ()
  (command "offset" "1150")
)
(defun c:1200 ()
  (command "offset" "1200")
)
(defun c:1250 ()
  (command "offset" "1250")
)
(defun c:1300 ()
  (command "offset" "1300")
)
(defun c:1350 ()
  (command "offset" "1350")
)
(defun c:1400 ()
  (command "offset" "1400")
)
(defun c:1450 ()
  (command "offset" "1450")
)
(defun c:1500 ()
  (command "offset" "1500")
)
(defun c:1550 ()
  (command "offset" "1550")
)
(defun c:1600 ()
  (command "offset" "1600")
)
(defun c:1650 ()
  (command "offset" "1650")
)
(defun c:1700 ()
  (command "offset" "1700")
)
(defun c:1750 ()
  (command "offset" "1750")
)
(defun c:1800 ()
  (command "offset" "1800")
)
(defun c:1850 ()
  (command "offset" "1850")
)
(defun c:1900 ()
  (command "offset" "1900")
)
(defun c:1950 ()
  (command "offset" "1950")
)
(defun c:2000 ()
  (command "offset" "2000")
)
(defun c:2100 ()
  (command "offset" "2100")
)
(defun c:2200 ()
  (command "offset" "2200")
)
(defun c:2300 ()
  (command "offset" "2300")
)
(defun c:2400 ()
  (command "offset" "2400")
)
(defun c:2500 ()
  (command "offset" "2500")
)
(defun c:2600 ()
  (command "offset" "2600")
)
(defun c:2700 ()
  (command "offset" "2700")
)
(defun c:2800 ()
  (command "offset" "2800")
)
(defun c:2900 ()
  (command "offset" "2900")
)
(defun c:3000 ()
  (command "offset" "3000")
)
(defun c:3100 ()
  (command "offset" "3100")
)
(defun c:3200 ()
  (command "offset" "3200")
)
(defun c:3300 ()
  (command "offset" "3300")
)
(defun c:3400 ()
  (command "offset" "3400")
)
(defun c:3500 ()
  (command "offset" "3500")
)
(defun c:3600 ()
  (command "offset" "3600")
)
(defun c:3700 ()
  (command "offset" "3700")
)
(defun c:3800 ()
  (command "offset" "3800")
)
(defun c:3900 ()
  (command "offset" "3900")
)
(defun c:4000 ()
  (command "offset" "4000")
)
(defun c:4100 ()
  (command "offset" "4100")
)
(defun c:4200 ()
  (command "offset" "4200")
)
(defun c:4300 ()
  (command "offset" "4300")
)
(defun c:4400 ()
  (command "offset" "4400")
)
(defun c:4500 ()
  (command "offset" "4500")
)
(defun c:4600 ()
  (command "offset" "4600")
)
(defun c:4700 ()
  (command "offset" "4700")
)
(defun c:4800 ()
  (command "offset" "4800")
)
(defun c:4900 ()
  (command "offset" "4900")
)
(defun c:5000 ()
  (command "offset" "5000")
)
(defun c:5100 ()
  (command "offset" "5100")
)
(defun c:5200 ()
  (command "offset" "5200")
)
(defun c:5300 ()
  (command "offset" "4300")
)
(defun c:4300 ()
  (command "offset" "5300")
)
(defun c:5400 ()
  (command "offset" "5400")
)
(defun c:5500 ()
  (command "offset" "5500")
)
(defun c:5600 ()
  (command "offset" "5600")
)
(defun c:5700 ()
  (command "offset" "5700")
)
(defun c:5800 ()
  (command "offset" "5800")
)
(defun c:5900 ()
  (command "offset" "5900")
)
(defun c:6000 ()
  (command "offset" "6000")
)
(defun c:6100 ()
  (command "offset" "6100")
)
(defun c:6200 ()
  (command "offset" "6200")
)
(defun c:6300 ()
  (command "offset" "6300")
)
(defun c:6400 ()
  (command "offset" "6400")
)
(defun c:6500 ()
  (command "offset" "6500")
)
(defun c:6600 ()
  (command "offset" "6600")
)
(defun c:6700 ()
  (command "offset" "6700")
)
(defun c:6800 ()
  (command "offset" "6800")
)
(defun c:6900 ()
  (command "offset" "6900")
)
(defun c:7000 ()
  (command "offset" "7000")
)
(defun c:7100 ()
  (command "offset" "7100")
)
(defun c:7200 ()
  (command "offset" "7200")
)
(defun c:7300 ()
  (command "offset" "7300")
)
(defun c:7400 ()
  (command "offset" "7400")
)
(defun c:7500 ()
  (command "offset" "7500")
)
(defun c:7600 ()
  (command "offset" "7600")
)
(defun c:7700 ()
  (command "offset" "7700")
)
(defun c:7800 ()
  (command "offset" "7800")
)
(defun c:7900 ()
  (command "offset" "7900")
)
(defun c:7900 ()
  (command "offset" "7900")
)
(defun c:8000 ()
  (command "offset" "8000")
)
(defun c:8100 ()
  (command "offset" "8100")
)
(defun c:8200 ()
  (command "offset" "8200")
)
(defun c:8300 ()
  (command "offset" "8300")
)
(defun c:8400 ()
  (command "offset" "8400")
)
(defun c:8500 ()
  (command "offset" "8500")
)
(defun c:8600 ()
  (command "offset" "8600")
)
(defun c:8700 ()
  (command "offset" "8700")
)
(defun c:8800 ()
  (command "offset" "8800")
)
(defun c:8900 ()
  (command "offset" "8900")
)
(defun c:9000 ()
  (command "offset" "9000")
)
(defun c:9100 ()
  (command "offset" "9100")
)
(defun c:9200 ()
  (command "offset" "9200")
)
(defun c:9300 ()
  (command "offset" "9300")
)
(defun c:9400 ()
  (command "offset" "9400")
)
(defun c:9500 ()
  (command "offset" "9500")
)
(defun c:9600 ()
  (command "offset" "9600")
)
(defun c:9700 ()
  (command "offset" "9700")
)
(defun c:9800 ()
  (command "offset" "9800")
)
(defun c:9900 ()
  (command "offset" "9900")
)
(defun c:10000 ()
  (command "offset" "10000")
)
(defun c:11000 ()
  (command "offset" "11000")
)
(defun c:12000 ()
  (command "offset" "12000")
)
(defun c:13000 ()
  (command "offset" "13000")
)
(defun c:14000 ()
  (command "offset" "14000")
)
(defun c:15000 ()
  (command "offset" "15000")
)
(defun c:16000 ()
  (command "offset" "16000")
)
(defun c:17000 ()
  (command "offset" "17000")
)
(defun c:18000 ()
  (command "offset" "18000")
)
(defun c:19000 ()
  (command "offset" "19000")
)
****************************
)
(defun c:dh ()
  (command "dim" "hor")
)
(defun c:du ()
  (command "dim" "update")
)
