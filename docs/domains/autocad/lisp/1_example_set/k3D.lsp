KHUNG KHONG GIAN


     Khung tao tu cac dot la cac chop day vuong, nut la cac khoi cau, cac thanh la cac ong tru.
     Chu y : co the xoa mot so nut de tao ra cac hinh thuc khung, mai moi
-------------------------------------------------------------------------------------


   (defun NDLK ()
       (setq a (getint " do dai mot dot : ")
            h (getint " do cao mot dot : ")
            bkc (getint " ban kinh cau nut : ")
            bkt (getint " ban kinh ong tru : ")
            smx (getint " so dot theo phuong x : ")
            smy (getint " so dot theo phuong y : ")
            st (getint " so tang { <= min so dot theo phuong x, y } : ")
            P0 (getpoint " cho hinh chieu bang goc khung : ")
       )
   )
   (defun SLDLK ()
       (setq P1 (polar P0 0 a)
             P2 (polar P0 (/ pi 2) a)
             P3 (list (car P0) (cadr P0) a)
             G0 (polar P0 (/ pi 4) (/ a (sqrt 2)))
             D0 (list (car G0) (cadr G0) h)
             G1 (polar P0 0 (/ a 2))
             G2 (polar P0 (/ pi 2) (/ a 2))
             P4 (polar P2 0 a)
       )
   )
   (defun VTXK ()
      (command "UCS" "3" P0 G0 P3)
       (setq Pm (trans P0 0 1))
       (setq Dm (trans D0 0 1))
             (setq gn (angle Pm Dm))
       (setq D1 (polar Dm (+ gn (/ pi 2)) (/ bkt 2))
             D11 (polar D1 (+ gn pi) (* bkt 4))
             D111 (polar D11 (+ gn (/ pi 2)) (/ bkt 2))
             D2 (polar Pm (+ gn (/ pi 2)) (/ bkt 2))
             D22 (polar D2 gn (* bkt 4))
             D222 (polar D22 (+ gn (/ pi 2)) (/ bkt 2))
       )
       (command "PlINE" Pm Dm D1 D11 D111 D222 D22 D2 Pm "")  (setq  S5 (ssget "L"))
       (command "REVOLVE" S5 "" Pm Dm "")  (setq SS0 (ssget "L"))
       (command "UCS" "W")
       (command "ARRAY" SS0 "" "P" (list (+ (car P0) (/ a 2))
                                         (+ (cadr P0) (/ a 2))  )
                                   4 "" "")
           (setq P11 (polar P1 (* 7 (/ pi 4)) (* 2 bkc))
                 P22 (polar P2 (* 3 (/ pi 4)) (* 2 bkc))
           )
       (setq SS1 (ssget "W" P11 P22))
   ) 
   (defun VKXK ()
      (setq t 0)
      (while (< t st)
         (setq n 0)
         (while (< n (- smy t)) 
           (setq m 0)
           (while (< m (- smx t)) 
              (command "COPY" SS1 "" D0 (list (+ (+ (car D0) (* t (/ a 2))) (* m a))
                                              (+ (+ (cadr D0) (* t (/ a 2))) (* n a))
                                              (+ h (* t h))
                                        )        
              )
              (setq m (1+ m)) 
           )
         (setq n (1+ n))
         )
      (setq t (1+ t))
      )
   )
   (defun VTNK ()
      (command "UCS" "3" P0 P2 P3)
         (setq cent1 (trans P0 0 1))
         (setq cent2 (list (car cent1) (cadr cent1) (* bkt 4)))
      (command "CYLINDER" cent1 (/ bkt 2) a)  (setq S3 (ssget "L"))
      (command "CYLINDER" cent2 bkt (- a (* bkt 8))) (setq S33 (ssget "L"))
      (command "UCS" "W") 
      (command "UCS" "3" P0 P3 P1)
         (setq cen1 (trans P0 0 1))
         (setq cen2 (list (car cen1) (cadr cen1) (* bkt 4)))
      (command "CYLINDER" cen1 (/ bkt 2) a)   (setq S4 (ssget "L"))
      (command "CYLINDER" cen2 bkt (- a (* bkt 8))) (setq S44 (ssget "L"))
      (command "UCS" "W") 
   )
   (defun VKN1K ()
      (setq t 0)
      (while (<= t st)
         (setq n 0)
         (while (<= n (- smy t)) 
           (setq m 0)
           (while (< m (- smx t)) 
              (command "COPY" S3 S33 "" P0 (list (+ (+ (car P0) (* t (/ a 2))) (* m a))
                                             (+ (+ (cadr P0) (* t (/ a 2))) (* n a))
                                             (* t h)
                                       )        
              )
              (setq m (1+ m)) 
           )
         (setq n (1+ n))
         )
      (setq t (1+ t))
      )
   )
   (defun VKN2K ()
      (setq t 0)
      (while (<= t st)
         (setq n 0)
         (while (< n (- smy t)) 
           (setq m 0)
           (while (<= m (- smx t)) 
              (command "COPY" S4 S44 "" P0 (list (+ (+ (car P0) (* t (/ a 2))) (* m a))
                                             (+ (+ (cadr P0) (* t (/ a 2))) (* n a))
                                             (* t h)
                                       )        
              )
              (setq m (1+ m)) 
           )
         (setq n (1+ n))
         )
      (setq t (1+ t))
      )
   )
   (defun VNCK ()
      (command "SPHERE" P0 bkc)    (setq S1 (ssget "L"))
      (setq t 0)
      (while (<= t st)
         (setq n 0)
         (while (<= n (- smy t)) 
           (setq m 0)
           (while (<= m (- smx t)) 
              (command "COPY" S1 "" P0 (list (+ (+ (car P0) (* t (/ a 2))) (* m a))
                                             (+ (+ (cadr P0) (* t (/ a 2))) (* n a))
                                             (* t h)
                                       )        
              )
              (setq m (1+ m)) 
           )
         (setq n (1+ n))
         )
      (setq t (1+ t))
      )
   )
   (defun C:K3D ()
       (command "UCS" "W")
       (command "OSMODE" 0)
       (NDLK)
       (SLDLK)
       (VTXK) (VKXK)
       (VTNK) (VKN1K) (VKN2K)
       (VNCK)
    )
