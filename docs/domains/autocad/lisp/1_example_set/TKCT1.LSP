; Chuong trinh lap bang thong ke cot thep
;
(vmon)
(defun C:TKCT1 (/ Cm Bl Pw S p1 p2 p3 p4 p5 p6 p7 p8 p9 p10 p11 p12 p13 p14 p15 p16 p17 p18
p19 p20 p21 p22 Zoom1 Zoom2)
 (setq Cm (getvar "CMDECHO"))
 (setq Bl (getvar "BLIPMODE"))
 (setq Pw (getvar "PLINEWID"))
 (setvar "CMDECHO" 0)
 (setvar "BLIPMODE" 0)
 (initget 1)
 (setq p1 (getpoint "\nChon diem bat dau bang thong ke vat lieu:"))
 (initget 7)
 (setq S (getint "\nSo loai ki hieu thep:"))
 (setq p2 (polar p1 (/ (* Pi 3) 2) (+ 18 (* 14 S))))
 (setq p3 (polar p2 0 234))
 (setq p4 (polar p1 0 234))
 (setq p5 (polar p1 0 14))
 (setq p6 (polar p2 0 14))
 (setq p7 (polar p5 0 55))
 (setq p8 (polar p6 0 55))
 (setq p9 (polar p7 0 14))
 (setq p10 (polar p8 0 14))
 (setq p11 (polar p9 0 17))
 (setq p12 (polar p10 0 17))
 (setq p13 (polar p11 0 67))
 (setq p14 (polar p12 0 67))
 (setq p15 (polar p11 (/ (* Pi 3) 2) 9))
 (setq p16 (polar p15 0 134))
 (setq p17 (polar p15 0 34))
 (setq p18 (polar p12 0 34))
 (setq p19 (polar p17 0 67))
 (setq p20 (polar p14 0 34))
 (setq p21 (polar p1 (/ (* Pi 3) 2) 18))
 (setq p22 (polar p21 0 234))
 (setq Zoom1 (polar p1 (* (/ Pi 4) 3) 10))
 (setq Zoom2 (polar p3 (* (/ Pi 4) 7) 10))
 (command "Zoom" "Window" Zoom1 Zoom2)
 (command "Plinewid" "0.5")
 (command "Pline" p1 p2 p3 p4 p1 "")
 (command "Line" p5 p6 "")
 (command "Line" p7 p8 "")
 (command "Line" p9 p10 "")
 (command "Line" p11 p12 "")
 (command "Line" p13 p14 "")
 (command "Line" p17 p18 "")
 (command "Line" p19 p20 "")
 (command "Line" p15 p16 "")
 (command "Line" p21 p22 "")
 (command "Array" "l" "" "Rec" S "1" "-14")
 (command "Insert" "bang1" p1 "" "" "0")
 (setvar "BLIPMODE" Bl)
 (setvar "CMDECHO" Cm)
 (setvar "PLINEWID" Pw)
)
(princ "  TKCT1 loaded.  ")
(princ)
---------------------------------------------------------------------------------------
(vmon)
(defun C:TKCT2 (/ Cm Bl Pw S a1 a2 a3 p1 p2 p3 p4 p5 p6 p7 p8 p9 p10 p11 p12 p13 p14 p15 p16 p17 p18
p19 p20 p21 p22 Zoom1 Zoom2)
 (setq Cm (getvar "CMDECHO"))
 (setq Bl (getvar "BLIPMODE"))
 (setq Pw (getvar "PLINEWID"))
 (setvar "CMDECHO" 0)
 (setvar "BLIPMODE" 0)
 (initget 1)
 (setq a1 (getpoint "\nChon diem bat dau bang thong ke vat lieu:"))
 (initget 7)
 (setq S (getint "\nSo loai ki hieu thep:"))
 (setq a2 (polar a1 (* (/ Pi 2) 3) (+ 18 (* 14 S))))
 (setq a3 (polar a1 (* (/ Pi 2) 3) 18))
 (setq p1 (polar a1 0 14))
 (setq p2 (polar p1 (/ (* Pi 3) 2) (+ 18 (* 14 S))))
 (setq p3 (polar p2 0 234))
 (setq p4 (polar p1 0 234))
 (setq p5 (polar p1 0 14))
 (setq p6 (polar p2 0 14))
 (setq p7 (polar p5 0 55))
 (setq p8 (polar p6 0 55))
 (setq p9 (polar p7 0 14))
 (setq p10 (polar p8 0 14))
 (setq p11 (polar p9 0 17))
 (setq p12 (polar p10 0 17))
 (setq p13 (polar p11 0 67))
 (setq p14 (polar p12 0 67))
 (setq p15 (polar p11 (/ (* Pi 3) 2) 9))
 (setq p16 (polar p15 0 134))
 (setq p17 (polar p15 0 34))
 (setq p18 (polar p12 0 34))
 (setq p19 (polar p17 0 67))
 (setq p20 (polar p14 0 34))
 (setq p21 (polar p1 (/ (* Pi 3) 2) 18))
 (setq p22 (polar p21 0 234))
 (setq Zoom1 (polar a1 (* (/ Pi 4) 3) 10))
 (setq Zoom2 (polar p3 (* (/ Pi 4) 7) 10))
 (command "Zoom" "Window" Zoom1 Zoom2)
 (command "Plinewid" "0.5")
 (command "Pline" a1 a2 p3 p4 a1 "")
 (command "Line" p5 p6 "")
 (command "Line" p7 p8 "")
 (command "Line" p9 p10 "")
 (command "Line" p11 p12 "")
 (command "Line" p13 p14 "")
 (command "Line" p17 p18 "")
 (command "Line" p19 p20 "")
 (command "Line" p15 p16 "")
 (command "Line" a3 p21 "")
 (command "Line" p1 p2 "")
 (command "Line" p21 p22 "")
 (command "Array" "l" "" "Rec" S "1" "-14")
 (command "Insert" "bang2" a1 "" "" "0")
 (setvar "BLIPMODE" Bl)
 (setvar "CMDECHO" Cm)
 (setvar "PLINEWID" Pw)
)
(princ "  TKCT2 loaded.  ")
(princ)
