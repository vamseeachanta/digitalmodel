(defun c:len ()
; this will create layer for you
;(PROMPT "\n***WARNING***\nSELECT ONLY LINE ENTITY.")
  (setq	linsel (ssget)
	Newlay (getstring "\nEnter new Layer name: ")
	b      (sslength linsel)
	c      0
  )
(command "layer" "m" newlay "")
  (setq linlen 0)
  (while (< c b)
    (setq selent (ssname linsel c))
					;(setq filsel (car selent))
    (setq entlist (entget selent))
    (setq fpt (cdr (assoc 10 entlist)))
    (setq spt (cdr (assoc 11 entlist)))
    (setq lindist (distance fpt spt))
    (command "chprop" selent "" "la" newlay "c" "1" "")
    (setq findist (+ linlen lindist))
    (Prompt (strcat "\r\tLength is: " (rtos findist 2 8)))
    (setq linlen findist)
    (setq c (1+ c))
  )
  (prompt (strcat "\nTotal Length is: " (rtos linlen 2 8)))
  (princ)
)
