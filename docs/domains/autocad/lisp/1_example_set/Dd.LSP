(DEFUN C:Dbb()
(defun *error* (msg)
	(princ "error: ")
	(princ msg)
	(terpri)
)
	(COMMAND "COLOR" "bylayer")
	(command "layer" "make" "dist" "")
	(command "LAYER" "THAW" "DIST" "")
	(command "LAYER" "SET" "DIST" "c" 3"" "")
        (command "osnap" "node")
        (WHILE (SETQ pn (GETlines "\nplease select your objects"))
		(SETQ DS (DISTANCE SP EP))
		(SETQ ANG (ANGLE SP EP))
		(SETQ D2 (/ DS 2))
		(setq pi2 (/ pi 2))
		(SETQ M2 (POLAR SP ANG D2))
		(setq ang1 (+ ang pi2))
                (SETQ M3 (POLAR m2 ANG1 2))
		(SETQ DS (RTOS DS 2 2))
		(setq deg (/ (* ang 180) pi))
		(COMMAND "TEXT" "m" M3 3 deg DS)
	)
)
