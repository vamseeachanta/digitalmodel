;load program then enter wrco at command line
(defun c:WG (/)
(setq obm (getvar "blipmode")) 
(setq oom (getvar "osmode"))
  (setq andr(getvar"angdir"))
 (setvar "angdir"1)
 (setq andb(getvar"angbase")) 
(setvar "angbase"(/ pi 2))
(setq aunt(getvar"aunits"))  
(setvar "aunits"2)
  (setvar "dimaunit"2)
  (setvar"dimadec"4)
  
(while
    (setq osmd (getvar "osmode"))
    (initget 1)
    (setq px (getpoint "\n click the point "))
    (setq osmd (getvar "osmode"))
    (initget 1)
    (setq pt (getpoint px "\n click for place for writing"))
    (setq y (cadr px))
    (setq x (car px))
    (setq z(last px))
  (if(null z)
    (setq z z))
  (setq znew(getreal(strcat"\n CL:<"(rtos z 2 3)">:")))
(if znew(setq z znew))
(setvar "osmode"0)
    (setvar"textstyle" "standard")
    (setq IL (getstring 1"\n IL of the point(press enter for nothing):"))
    (if(null IL)(progn
    (command "_qleader" px pt""""(strcat"E:"(rtos x 2 3 ))
	     (strcat"N:"(rtos y 2 3 ))(strcat"CL:"(rtos z 2 2 )) "" "")));end of if
    (command "_qleader" px pt""""(strcat"E:"(rtos x 2 3 ))
	     (strcat"N:"(rtos y 2 3 ))(strcat"CL:"(rtos z 2 2 ))(strcat"IL:"IL))
  (setq tds(entlast))
    (initget 6)
  (setvar"angbase"andb)
  (setvar "angdir"andr)
  (setvar"aunits"aunt)
  (setvar"osmode"osmd)
  
    )
      )
