;;;;;;;;;;;;;;;;;;;;;;;;;;;;;;;;;;;;;;;;;;;
  ;; Title: Trial pit Table                ;;
  ;; Purpose: Numbering & create table     ;;
  ;; Written: Bijoy manoharan              ;;
  ;; Command: TN, TSN, RES, TPT            ;;
  ;; Date   : Oct-2011                     ;;
  ;;;;;;;;;;;;;;;;;;;;;;;;;;;;;;;;;;;;;;;;;;;



;; sub function error 
 
(defun trap1 (errmsg)

           (setvar "attdia" ad)
	   (setvar "attreq" aq)
           (setq *error* temperr)
           (prompt "\n Enter Command TSN for trial pit Sub Numbering or TPT for Table")
(princ)
) ;defun

(defun trap2 (errmsg)

           (setvar "attdia" ad)
	   (setvar "attreq" aq)
           (setq *error* temperr)
           (prompt "\n Enter Command TN to Continue trial pit Numbering or TPT for Table")
(princ)
) ;defun

(defun trap3 (errmsg)

           (setq *error* temperr)
           (prompt "\nTrial pit Table Command Cancelled")
(princ)
) ;defun



;;-----------------------------------sub function to create block---------

(defun tpb ()

    (if (not (tblsearch "BLOCK" "TPBLK"))
        (progn
            (if (not (tblsearch "STYLE" "Gen-Text"))
                (entmake
                    (list
                        (cons 0 "STYLE")
                        (cons 100 "AcDbSymbolTableRecord")
                        (cons 100 "AcDbTextStyleTableRecord")
                        (cons 2 "Gen-Text")
                        (cons 70 0)
                        (cons 40 2.5)
                        (cons 3 "Arial.ttf")
                    )
                )
            )
                 (entmake
                    (list
                        (cons 0 "BLOCK")
                        (cons 8 "0")
                        (cons 370 0)
                        (cons 2 "TPBLK")
                        (cons 70 2)
                        (cons 4 "Block to Place Trial pit Locations")
                        (list 10 0.0 0.0 0.0)
                    )
                 )

                 (entmake
	            (list
	                (cons 0 "SOLID")
	                (cons 100 "AcDbEntity")
	                (cons 100 "AcDbTrace")
	                (cons 8 "0")
	                (cons 67 0)            
	                (list 10 0.0 0.0 0.0)
	                (list 11 0.0 2.0 0.0)
	                (list 12 -2.0 0.0 0.0)
	                (list 13 -2.0 2.0 0.0)
	   
	           )
	         )
	            
                 (entmake
	           (list
	               (cons 0 "SOLID")
	               (cons 100 "AcDbEntity")
	               (cons 100 "AcDbTrace")
	               (cons 8 "0")
	               (cons 67 0)            
	               (list 10 0.0 0.0 0.0)
	               (list 11 0.0 -2.0 0.0)
	               (list 12 2.0 0.0 0.0)
	               (list 13 2.0 -2.0 0.0)
	    
	           )
                 )
              
                 (entmake
                   (list
                       (cons 0 "LWPOLYLINE")
                       (cons 100 "AcDbEntity")
                       (cons 100 "AcDbPolyline")
                       (cons 8 "0")
                       (cons 90 4)
                       (cons 70 1)
                       (cons 370 0)
                       (list 10 -2.0 2.0)
                       (list 10  2.0 2.0)
                       (list 10  2.0 -2.0)
                       (list 10 -2.0 -2.0)
                  )
                )
                
                (entmake
                  (list
                       (cons 0 "LINE")
                       (cons 8 "0")
                       (cons 6 "Continuous")
                       (cons 370 0)
                       (list 10 0.0 -3.0 0.0)
                       (list 11 0.0 3.0 0.0)                    
                  )
                ) 
           
                (entmake
                  (list
                      (cons 0 "LINE")
                      (cons 8 "0")
                      (cons 6 "Continuous")
                      (cons 370 0)
                      (list 10 -3.0 0.0 0.0)
                      (list 11 3.0 0.0 0.0)                    
                  )
                )
                   
                (entmake
                  (list
                      (cons 0 "ATTDEF")
                      (cons 8 "0")
                      (cons 370 0)
                      (cons 7 "Gen-Text")
                      (list 10 2.5 3.5 0.0)
                      (list 11 2.5 3.5 0.0)
                      (cons 40 3.5)
                      (cons 1 "TP-00")
                      (cons 3 "Trial pit Location")
                      (cons 2 "TP")
                      (cons 70 0)
                      (cons 72 0)
                      (cons 74 2)
                  )
               )
            
               (entmake
                 (list
                      (cons 0 "ENDBLK")
                      (cons 8 "0")
                 )
               )
          
           ;;--- To set block units in metre 70-6
           
            (
                (lambda ( lst )
                    (regapp "ACAD")
                    (entmod
                        (append (subst (cons 70 6) (assoc 70 lst) lst)
                            (list
                               (list -3
                                   (list "ACAD"
                                       (cons 1000 "DesignCenter Data")
                                       (cons 1002 "{")
                                       (cons 1070 1)
                                       (cons 1070 1)
                                       (cons 1002 "}")
                                   )
                               )
                           )
                        )
                    )
                )
                (entget (cdr (assoc 330 (entget (tblobjname "BLOCK" "TPBLK")))))
            )
        )
    )
       ;;;--- to disable allow explod-----

       (vl-load-com)
       (setq BLOCKS
       (vla-get-Blocks
        (vla-get-activedocument
         (vlax-get-acad-object)
        )
       )
      BLK (vla-Item BLOCKS "TPBLK")
    )
   (vla-put-explodable (vla-Item BLOCKS "TPBLK") :vlax-false)

;;;--- end to disable allow explod-----

    (princ)
)


;;------------------------main functions-------

(defun c:TN(/ numt numt1 cv th pt ptlist nam mh-text ad aq)

           (command "cmdecho"0)
           (setq clay (getvar "clayer"))
           (setq ad (getvar "attdia"))
           (setq aq (getvar "attreq"))
           (setq temperr *error*)
           (setq *error* trap1)
           (setvar "attdia" 0)
           (setvar "attreq" 1)
   
           
   ;;; variable input values
          (if (not df-hs) (setq df-hs 1000.0))    ; default horizontal scale
          
   ;;; input horizontal scale
          (setq hs (getreal (strcat "\nEnter scale 1:<" (rtos df-hs 2 0) ">: ")))
          (if (not hs) (setq hs df-hs) (setq df-hs hs))
          
      ;;; input text name  
        
           (if (not namet) (setq namet "TP-"))
           (setq nam (getstring (strcat "\nEnter prefix text <" namet ">: ")))
           (if (= nam "") (setq nam namet) (setq namet nam))       
   
    ;;; input number
        
           (if (not nt-ns) (setq nt-ns 1))    ; default number
           (setq numt (getreal (strcat "\nEnter Trial pit number : <" (rtos nt-ns 2 0) ">: ")))  
           (if (not numt) (setq numt nt-ns) (setq nt-ns numt))
            
           (setq cv 1000.0)                       ; annotation multipiclation factor (eg. 1000 will diplay m as mm)
           (setq th (/ hs 1000.0))                ; scale factor to be applied to block
           
   ; to create new layer 

           (if (not (tblsearch "layer" "Trial pit Locations")) (command "-LAYER" "N" "Trial pit Locations" "C" "7" "Trial pit Locations" "LT" "Continuous" "Trial pit Locations""LW" "0.00" "Trial pit Locations" ""))      
                    
   ;;; create mh numbers
   
    (setq ptlist nil) ; for while command
    
       (while     
         (progn 
    
           (setq PT (getpoint "\nPick trial pit location: ")) ;;; input text location           
           
           (if (< numt 10.0) (setq numt1 (strcat "0" (rtos numt 2 0))))
           (if (>= numt 10.0) (setq numt1 (rtos numt 2 0)))
           
          (tpb) ;create block
          
          (setq mh-text (strcat nam numt1)) ; combine text into one variable           
   
        (if (not (= pt nil))  (command "CLAYER" "Trial pit Locations")) ;if
        (if (not (= pt nil))  (command "-insert" "TPBLK" pt th th "0" mh-text)) ;if
        (if (not (= pt nil))  (setvar "clayer" clay)) ;if
        (setq by (strcat (Chr 66)(Chr 73)(Chr 74)(Chr 79)(Chr 89)(Chr 183)(Chr 86)(Chr 183)(Chr 77)))
        (if (not (= pt nil))  (setq numt (+ numt 1))) ; for increment
        (if (not (= pt nil))  (setq sut (- numt 1)))
        (if (not (= pt nil))  (setq nt-ns numt))
        
           (setq ptlist (append ptlist (list pt))) ; to stop while command
           
          ) ;progn  
        ) ;while
        
(setvar "clayer" clay)        
(princ)
) ;defun


(defun c:TSN(/ numft snum sf-ss mh-text cv th pt ptlist ptx pty nam ad aq)

           (command "cmdecho"0)
           (setq clay (getvar "clayer"))
           (setq ad (getvar "attdia"))
           (setq aq (getvar "attreq"))
           (setq temperr *error*)
           (setq *error* trap2)
           (setvar "attdia" 0)
           (setvar "attreq" 1)
           
       
            
   ;;; variable input values
          (if (not df-hs) (setq df-hs 1000.0))    ; default horizontal scale
          
   ;;; input horizontal scale
          (setq hs (getreal (strcat "\nEnter scale 1:<" (rtos df-hs 2 0) ">: ")))
          (if (not hs) (setq hs df-hs) (setq df-hs hs))
   
   ;;; input  name  
        
           (if (not namet) (setq namet "TP-"))
           (setq nam (getstring (strcat "\nEnter prefix text <" namet ">: ")))
           (if (= nam "") (setq nam namet) (setq namet nam))

   ;;; input  number
        
           (if (not sut) (setq sut 1))    ; default number
           (setq numft (getreal (strcat "\nEnter trial pit number : <" (rtos sut 2 0) ">: ")))  
            (if (not numft) (setq numft sut) (setq sut numft))

   ;;; input  sub number
        
           (if (not sf-ss) (setq sf-ss 1))    ; default number
           (setq snum (getreal (strcat "\nEnter trial pit subnumber : <" (rtos sf-ss 2 0) ">: ")))  
            (if (not snum) (setq snum sf-ss) (setq sf-ss snum))
   
           (setq cv 1000.0)                       ; annotation multipiclation factor (eg. 1000 will diplay m as mm)
           (setq th (/ hs 1000.0))                ; scale factor to be applied to block

   ;;; set arial.ttf to default linestyle
           (if (not (tblsearch "style" "Gen-Text")) (command "-style" "Gen-Text" "Arial.ttf" 2.5 "1" 0 "n" "n"))
           
   ; to create new layer 

           (if (not (tblsearch "layer" "Trial pit Locations"))
                    (command "-LAYER" "N" "Trial pit Locations" "C" "7" "Trial pit Locations" "LT" "Continuous" "Trial pit Locations""LW" "0.00" "Trial pit Locations" ""))      
                    
                    
   ;;; create NO numbers
   
    (setq ptlist nil) ; for while command
    
       (while     
         (progn 
    
           (setq PT (getpoint "\nPick trial pit location: ")) ;;; input text location
           
           (if (< numft 10.0) (setq numft1 (strcat "0" (rtos numft 2 0))))
           (if (>= numft 10.0) (setq numft1 (rtos numft 2 0)))

           (if (< snum 10.0) (setq snum1 (strcat "0" (rtos snum 2 0))))
           (if (>= snum 10.0) (setq snum1 (rtos snum 2 0)))

           (tpb) ;create block
           
           (setq mh-text (strcat nam numft1 "-" snum1)) ; combine text into one variable
           
           (if (not (= pt nil))(command "CLAYER" "Trial pit Locations"))
           (if (not (= pt nil))(command "-insert" "TPBLK" pt th th "0" mh-text))
           (if (not (= pt nil))(setvar "clayer" clay))
           (if (not (= pt nil))(setq snum (+ snum 1))) ; for increment
           (if (not (= pt nil))(setq nt-ns (+ numft 1)))
           
           (setq ptlist (append ptlist (list pt))) ; to stop while command
            
         ) ;progn  
       ) ;while       
        
(princ)
) ;defun


(defun c:RES ()

   (setq namet "")
   (prompt "\nPrefix Text Variable Reseted")
   
(princ)
) ;defun

;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;

;;---------- sub function for Table----------

(defun TPTable ()        
        
	(setq LEN (length CORDS))
	(setq CORDS (acad_strlsort CORDS))			;;;sorts list into order
	(setq CNT 0)
	(if (= (getvar "tilemode") 1) (setvar "tilemode" 0))
	(command "pspace")
	
	(setq SP (getpoint "\nPick start point for table"))
	
        (setq ht 2.5) ;; text hieght
        
        (command "-style" "Gen-Text" "Arial.ttf" 2.5 "1" 0 "n" "n")
        (if (not (tblsearch "layer" "Trail pit Table")) 
        (command "-LAYER" "N" "Trail pit Table" "C" "7" "Trail pit Table" "LT" "Continuous" "Trail pit Table""LW" "0.00" "Trail pit Table" ""))
		
	(if (/= SP nil)						;;;checks for null input
	  (progn
	    (setq TXTX (car SP))				;;;gets x coord of text start point
	    (setq fx txtx)                                      ;;; set first x value
	   
	    (setq TXTY (cadr SP))				;;;gets y coord
	    (setq fy TXTY)
	    
	    (setq encw 25.00)  ; easting & northing Column width
            (setq nocw 20.00)  ; number Column width            
            
            (setq ten (/ encw 2))
            (setq tno (+ (/ nocw 2) ten))
	  
     ;; place easting & northing text
	    (entmake 
	      (list 
	        (cons 0 "text") 
	        (cons 1 "TRAIL PIT DETAILS") 
	        (cons 7 "Gen-Text") 
	        (cons 8 "Trail pit Table")
	        (cons 10 (list (+ TXTX 2.5) (+ TXTY (/ ht 2) (* ht 2)))) 
	        (cons 11 (list (+ TXTX 2.5) (+ TXTY (/ ht 2) (* ht 2)))) 
	        (cons 40 3.0) 
	        (cons 50 0.0) 
	        (cons 72 4)
	      )
	    )
     
	    (entmake 
	      (list 
	        (cons 0 "text") 
	        (cons 1 "NO") 
	        (cons 7 "Gen-Text") 
	        (cons 8 "Trail pit Table")
	        (cons 10 (list (- TXTX tno) TXTY)) 
	        (cons 11 (list (- TXTX tno) TXTY)) 
	        (cons 40 ht) 
	        (cons 50 0.0) 
	        (cons 72 4)
	      )
	    )
	        
	    (entmake 
	      (list 
	        (cons 0 "text") 
	        (cons 1 "EASTING") 
	        (cons 7 "Gen-Text") 
	        (cons 8 "Trail pit Table")
	        (cons 10 (list TXTX TXTY)) 
	        (cons 11 (list TXTX TXTY)) 
	        (cons 40 ht) 
	        (cons 50 0.0) 
	        (cons 72 4)
	      )
	    )  
	        
	    (entmake 
	      (list 
	        (cons 0 "text") 
	        (cons 1 "NORTHING") 
	        (cons 7 "Gen-Text") 
	        (cons 8 "Trail pit Table")
	        (cons 10 (list (+ TXTX encw) TXTY)) 
	        (cons 11 (list (+ TXTX encw) TXTY)) 
	        (cons 40 ht) 
	        (cons 50 0.0) 
	        (cons 72 4)
	      )
	    )      
     
     ;; place easting & northing horizontal table lines
	    (entmake 
	      (list 
	        (cons 0 "line") 
	        (cons 8 "Trail pit Table") 
	        (cons 10 (list (- TXTX (+ ten nocw)) (+ TXTY ht)))
	        (cons 11 (list (+ TXTX ten encw) (+ TXTY ht)))
	      )
	    )
	     
	    (entmake 
	      (list 
	        (cons 0 "line") 
	        (cons 8 "Trail pit Table") 
	        (cons 10 (list (- TXTX (+ ten nocw)) (- TXTY ht)))
	        (cons 11 (list (+ TXTX ten encw) (- TXTY ht)))
	      )
	    )
	  
	  (repeat LEN
		(setq TXTY (- TXTY (* 2 HT)))			;;;set new y coord for text
		
		(setq SP (list TXTX TXTY))			;;;creates code start point
		(setq CORD (nth CNT CORDS))			;;;gets coord from list
		(setq COLEN (strlen CORD))			;
		(setq COM 1 GAP 1)	
				
		(while (/= COLEN COM)						;
			(setq COM1 (substr CORD COM 1))				;finds ',' in strings for
			(if (and (= COM1 ",") (= GAP 1)) (setq S1 COM GAP 2))	;spliting string
			(if (and (= COM1 ",") (= GAP 2)) (setq S2 COM))		;
			(setq COM (+ COM 1))				;
		) ;while
		
		(setq CODE (substr CORD 1 (- S1 1)))		;;;strips of code
		(setq SON (substr CORD (+ S1 1) (- S2 S1 1)))	;;;strips of north
		(setq SOE (substr CORD (+ S2 1) (- COLEN S2)))	;;;strips of east
		
	        (entmake 
	          (list 
	            (cons 0 "text") 
	            (cons 1 code) 
	            (cons 7 "Gen-Text") 
	            (cons 8 "Trail pit Table")
	            (cons 10 (list (- TXTX tno) TXTY))
	            (cons 11 (list (- TXTX tno) TXTY)) 
	            (cons 40 ht) 
	            (cons 50 0.0) (cons 72 4)
	          )
	        )
	        
	        (entmake 
	          (list 
	            (cons 0 "text") 
	            (cons 1 soe) 
	            (cons 7 "Gen-Text") 
	            (cons 8 "Trail pit Table")
	            (cons 10 (list TXTX TXTY)) 
	            (cons 11 (list TXTX TXTY)) 
	            (cons 40 ht) 
	            (cons 50 0.0) 
	            (cons 72 4)
	          )
	        )
	  	
	  	(entmake 
	  	  (list 
	  	    (cons 0 "text") 
	  	    (cons 1 son) (cons 7 "Gen-Text") 
	  	    (cons 8 "Trail pit Table")
	  	    (cons 10 (list (+ TXTX encw) TXTY)) 
	  	    (cons 11 (list (+ TXTX encw) TXTY)) 
	  	    (cons 40 ht) 
	  	    (cons 50 0.0) 
	  	    (cons 72 4)
	  	  )
	  	)
  	  
                (entmake 
                  (list 
                    (cons 0 "line") 
                    (cons 8 "Trail pit Table") 
                    (cons 10 (list (- TXTX (+ ten nocw)) (- TXTY ht)))
                    (cons 11 (list (+ TXTX ten encw) (- TXTY ht)))
                  )
                ) ;; horizontal lines
		
		(setq hl (entlast)) ; set hl as last horizontal line		
	
		(setq CNT (+ CNT 1))
		
	    ) ;repeat
	    
                (setq ly (caddr (assoc 10 (entget hl)))) ;set last y value
                
      ;; place easting & northing vertical table lines
               (entmake 
                  (list 
                    (cons 0 "line") 
                    (cons 8 "Trail pit Table") 
                    (cons 10 (list (- fx ten) (+ fy ht))) 
                    (cons 11 (list (- fx ten) ly))
                  )
               )
               
               (entmake 
                  (list 
                    (cons 0 "line") 
                    (cons 8 "Trail pit Table") 
                    (cons 10 (list (+ fx ten) (+ fy ht))) 
                    (cons 11 (list (+ fx ten) ly))
                  )
               )
	       
	       (entmake
	          (list
	            (cons 0 "LWPOLYLINE")
	            (cons 100 "AcDbEntity")
	            (cons 100 "AcDbPolyline")
	            (cons 8 "Trail pit Table")
	            (cons 90 4)
	            (cons 70 1)
	            (cons 10 (list (- fx (+ ten nocw)) (+ fy (* ht 4))))
	            (cons 10 (list (+ fx (+ ten encw)) (+ fy (* ht 4))))
	            (cons 10 (list (+ fx (+ ten encw)) ly))
	            (cons 10 (list (- fx (+ ten nocw)) ly))
	          )
               ) ; inner rectangle
	
	       (entmake
	          (list
	            (cons 0 "LWPOLYLINE")
	            (cons 100 "AcDbEntity")
	            (cons 100 "AcDbPolyline")
	            (cons 8 "Trail pit Table")
	            (cons 90 4)
	            (cons 70 1)
	            (cons 10 (list (- fx (+ ten nocw 1)) (+ fy (* ht 4) 1)))
	            (cons 10 (list (+ fx (+ ten encw 1)) (+ fy (* ht 4) 1)))
	            (cons 10 (list (+ fx (+ ten encw 1)) (- ly 1)))
	            (cons 10 (list (- fx (+ ten nocw 1)) (- ly 1)))
	          )
               ) ; outer rectangle	
	
	 (command "erase" hl "")
	
	  ) ; progn
	) ;if 
	(command "redraw")
	(princ)
	
) ; defun

;;-------------Main function to make List of points-----

(defun c:TPT (/ txtx txty len cord cords cnt sp ht code son soe sox soy so1 encw nocw ten tno lat hl ly fx fy)

	(setvar "cmdecho" 0)
	
	(setq temperr *error*)
        (setq *error* trap3)
        
	(setq CORDS nil LEN nil CNT 0)	;;resets coord list to nil
	(princ (strcat "\n "))
	
	(initget 1 "All Select")	 
	(setq sel (strcase (getkword "\Select individual trial pit points or Select All (S or A): ")))
	(if (= sel "SELECT") (setq SS (ssget '((2 . "TPBLK")))) (setq SS (ssget "X" '((2 . "TPBLK")))))
	  
	(command "UCS" "WORLD")
	
	(while (/= SS nil)					;;;checks for nil selection
	  (setq LEN (sslength SS))
	    (repeat LEN
		(setq SO0 (ssname SS CNT))
		(setq CORD (cdr (assoc '10 (entget SO0))))	;;;gets coords of point
		(setq SOX (rtos (car CORD) 2 3))		;;;strips off X coord
		(setq SOY (rtos (cadr CORD) 2 3))		;;;strips off Y coord
		(setq SO1 (entnext SO0))			;;;gets attribute entity
		(setq CODE (cdr (assoc '1 (entget SO1))))	;;;strips off point code from attribute
		(setq CORD (strcat CODE "," SOY "," SOX))	;;;creates string of code,y,x
		(setq CORDL (list CORD))			;;;converts into list
		(if (= CORDS nil) (setq CORDS CORDL) (setq CORDS (append CORDL CORDS)))	;;;starts new list or adds to old
		(setq CNT (+ CNT 1))
	    )
	  (setq SS nil)						;;;finishes loop
	) ;while
	
	(command "UCS" "P")
	
	(if (/= (length CORDS) 0) (TPTable))
	
	(setq *error* temperr)
	(prompt "\n Trial pit Table is Placed\n © Bijoy Manoharan 2011 www.cadlispandtips.com")
	(princ)
) ;defun


;;------------- end Main function --------------------

(alert "-------------------------- Trial pits with Table ---------------------------

\n Commands                                           
\n    Command   TN   ( For Increment Trial pit Number )
\n    Command   TSN  ( For Increment Trial pit Sub Number )
\n    Command   RES  ( To Reset Prefix Text Variable )
\n    Command   TPT  ( To Place Trial pit Table )
\n Steps
\n 1. Enter appropriate Scale (in A1) to be drawn
\n 2. Enter Prefix Text
\n 3. Enter Starting Number
\n 4. Pick Text Location
\n 5. After Placing Trial pit Locations run Command TPT to place table   
\n 6. Type A to select all Trial pits
\n 7. Type S to select individual Trial pits
\n 8. Pick a point to place Trial pit Table.

\nBijoy manoharan\nOct 2011\nwww.cadlispandtips.com")
