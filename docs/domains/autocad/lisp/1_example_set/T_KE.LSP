;;; TK.LSP Version 1.2, Copyright (C) (1996) by Pham Hoang Anh, K37-X6 
;;; ===========================================================================
(defun C:TK ( /
             l1     l2         l3     
             sh     style      dk     dai     sl1     slck     sla    dt     tl   
             p0   p1    p2    p3    p4    p5    p6    p7    p8    p9 
             nhap   thongke    ve
            )
;------------dat bat dinh---------------------------
(defun set_osnap ( os ) 
 (if (= 1 os)
   (progn
     (SETVAR "OSMODE" 177)
     (SETVAR "BLIPMODE" 1)
   )
   (progn
     (SETVAR "OSMODE" 0)
     (SETVAR "BLIPMODE" 0)
   )
 )
)
;------------nhap so lieu---------------------------
(defun nhap ()
 ;;--------nhap chieu dai---------------
 (defun nhap_chieu_dai ()
  ;;;--------nhap1-----------
  (defun nhap1 ()
   (initget 1)
   (setq l2 (getreal "\nChieu dai (mm): "))
  )
  ;;;--------nhap2-----------
  (defun nhap2 ()
   (princ             "Chieu dai (mm):")
   (initget 1)
   (setq l1 (getreal "\n       l1 = "))
   (initget 1)
   (setq l2 (getreal "\n       l2 = "))
  )
  ;;;--------nhap3-----------
  (defun nhap3 ()
               (princ "Chieu dai (mm):")
   (initget 1)
   (setq l1 (getreal "\n       l1 = "))
   (initget 1)
   (setq l2 (getreal "\n       l2 = "))
   (initget 1)
   (setq l3 (getreal "\n       l3 = "))
  )
  ;;;------------------------ 
  (cond
       ( (or (= 0 style) (= 1 style) (= 2 style) (= 21 style)) (nhap1) )
       ( (or (= 4 style) (= 5 style)) (nhap2) )
       ( (or (= 3 style) (= 31 style)) (nhap3) )
       (t) 
  )
 )
 ;;-------------------------------------
 (setq p0 4.5)
 (initget 1)
 (setq p1 (getpoint "\nDiem chen : ")
       p2 (polar p1 0 10) 
       p3 (polar p2 0 50)
       p4 (polar p3 0 10) 
       p5 (polar p4 0 20) 
       p6 (polar p5 0 15) 
       p7 (polar p6 0 15) 
       p8 (polar p7 0 20) 
       p9 (polar p8 0 20) 
 )
 (initget 1)
 (setq sh (getstring "\nSo hieu : "))
 (initget 1)
 (setq style (getint "\nKieu : "))
 (initget 1)
 (setq dk (getint "\nDuong kinh (mm): "))
 (nhap_chieu_dai)
 (initget 1)
 (setq sl1 (getint "\nSo luong cho 1 c.k : "))
 (initget 1)
 (setq slck (getint "\nSo luong cau kien : "))
)
;-------------------------------------------
;------------thong ke---------------------------
(defun thongke ( / dkinh dtich )
 ;;----------tinh chieu dai thanh--------------
 (defun tinh_chieu_dai ()
  ;;;---------tinh 1--------------------------
  (defun tinh1 ()
    (setq dai l2) 
  )
  ;;;---------tinh 2--------------------------
  (defun tinh2 ()
   (cond 
       ( (= 6 dk)  (setq l1 50) )
       ( (= 8 dk)  (setq l1 60) )
       ( (= 10 dk) (setq l1 80) )
       (t)
   )
   (setq l3 l1)
   (setq dai (+ l1 (+ l2 l3)) )
  )
  ;;;---------tinh 3--------------------------
  (defun tinh3 ()
   (setq dai (+ l1 (+ l2 l3)) )
  )
  ;;;---------tinh 4--------------------------
  (defun tinh4 ()
   (setq dai (+ l1 l2) )
  )
  ;;;---------tinh 5--------------------------
  (defun tinh5 ()
   (cond 
       ( (= 6 dk)  (setq l3 50) )
       ( (= 8 dk)  (setq l3 60) )
       ( (= 10 dk) (setq l3 80) )
       (t)
   )
   (setq dai (* 2 (+ l1 (+ l2 l3))) )
  )
  ;;;-----------------------------------------
  (cond
      ( (or (= 0 style) (= 1 style)) (tinh1) ) 
      ( (or (= 2 style) (= 21 style)) (tinh2) ) 
      ( (or (= 3 style) (= 31 style)) (tinh3) ) 
      ( (= 4 style) (tinh4) ) 
      ( (= 5 style) (tinh5) ) 
      (t)
  )
 ) 
 ;;------------------------------------------
 (tinh_chieu_dai)
 (setq dkinh (* dk 0.001))
 (setq dtich (* (* pi (* dkinh dkinh)) 0.25) )
 (setq sla (* sl1 slck))
 (setq dt (* (* dai sla) 0.001) )
 (setq tl (* (* 7850 dtich) dt) )
)
;---------------ve thong ke---------------------
(defun ve ()
 ;;---------------text_left---------------------
 (defun left ( l_p txt)
  (command "TEXT" "ML" l_p "" "" txt)
 )
 ;;---------------text_center------------------
 (defun center ( c_p txt)
  (command "TEXT" "MC" c_p "" "" txt)
 )
 ;;---------------text_right-------------------
 (defun right ( r_p txt)
  (command "TEXT" "MR" r_p "" "" txt)
 )
 ;;---------------text0------------------------
 (defun text0 ( / txt_p)
  (setq txt_p (list (+ 5 (car p1)) (+ p0 (cadr p1)) ) )
  (center txt_p sh)
  (setq txt_p (list (+ 5 (car p3)) (+ p0 (cadr p3)) ) )
  (center txt_p (itoa dk))
  (setq txt_p (list (+ 15 (car p4)) (+ p0 (cadr p4)) ) )
  (right txt_p (rtos dai 2 0))
  (setq txt_p (list (+ 10 (car p5)) (+ p0 (cadr p5)) ) )
  (right txt_p (itoa sl1))
  (setq txt_p (list (+ 10 (car p6)) (+ p0 (cadr p6)) ) )
  (right txt_p (itoa sla))
  (setq txt_p (list (+ 15 (car p7)) (+ p0 (cadr p7)) ) )
  (right txt_p (rtos dt 2 1))
  (setq txt_p (list (+ 15 (car p8)) (+ p0 (cadr p8)) ) )
  (right txt_p (rtos tl 2 1))
 )
 ;;---------------text1------------------------
 (defun text1 ( / txt_p)
  (setq txt_p (list (+ 25 (car p2)) (+ p0 (cadr p2)) ) )
  (center txt_p (rtos dai 2 0))
 )
 ;;---------------text2------------------------
 (defun text2 ( / txt_p)
  (setq txt_p (list (+ 9 (car p2)) (+ p0 (cadr p2)) ) )
  (right txt_p (rtos l1 2 0))
  (setq txt_p (list (+ 25 (car p2)) (+ p0 (cadr p2)) ) )
  (center txt_p (rtos l2 2 0))
  (setq txt_p (list (+ 41 (car p2)) (+ p0 (cadr p2)) ) )
  (left txt_p (rtos l3 2 0))
 )
 ;;---------------text21------------------------
 (defun text21 ( / txt_p)
  (setq txt_p (list (+ 14 (car p2)) (+ p0 (cadr p2)) ) )
  (right txt_p (rtos l1 2 0))
  (setq txt_p (list (+ 25 (car p2)) (+ p0 (cadr p2)) ) )
  (center txt_p (rtos l2 2 0))
  (setq txt_p (list (+ 36 (car p2)) (+ p0 (cadr p2)) ) )
  (left txt_p (rtos l3 2 0))
 )
 ;;---------------text4------------------------
 (defun text4 ( / txt_p)
  (setq txt_p (list (+ 9 (car p2)) (+ p0 (cadr p2)) ) )
  (right txt_p (rtos l1 2 0))
  (setq txt_p (list (+ 25 (car p2)) (+ p0 (cadr p2)) ) )
  (center txt_p (rtos l2 2 0))
 )
 ;;---------------text5------------------------
 (defun text5 ( / txt_p)
  (setq txt_p (list (+ 14 (car p2)) (+ p0 (cadr p2)) ) )
  (right txt_p (rtos l1 2 0))
  (setq txt_p (list (+ 25 (car p2)) (+ p0 (cadr p2)) ) )
  (center txt_p (rtos l2 2 0))
  (setq txt_p (list (+ 36 (car p2)) (+ p0 (cadr p2)) ) )
  (left txt_p (rtos l3 2 0))
 )
 ;;
 ;;---------------ve0-------------------------
 (defun ve0 ()
  (text0)
 )
 ;;---------------ve1-------------------------
 (defun ve1 ( / pt1 pt2)
  (setq pt1 (list (+ 10 (car p2)) (+ 2 (cadr p2)) ) )
  (setq pt2 (polar pt1 0 30) )
  (command "PLINE" pt1 pt2 "")
  (text1)
  (text0)
 )
 ;;---------------ve2-------------------------
 (defun ve2 ( / pt1 pt2 pt3 pt4 pt5 pt6)
  (setq pt1 (list (+ 10.75 (car p2)) (+ 2 (cadr p2)) ) )
  (setq pt2 (polar pt1 0 28.5) )
  (setq pt3 (polar pt1 (/ pi 2) 1.5) )
  (setq pt4 (polar pt2 (/ pi 2) 1.5) )
  (setq pt5 (polar pt3 0 2.5) )
  (setq pt6 (polar pt4 0 -2.5) )
  (command "PLINE" pt5 pt3 "A" pt1 "L" pt2 "A" pt4 "L" pt6 "")
  (text2)
  (text0)
 )
 ;;---------------ve21-------------------------
 (defun ve21 ( / pt1 pt2 pt3 pt4 pt5 pt6)
  (setq pt1 (list (+ 15.75 (car p2)) (+ 2 (cadr p2)) ) )
  (setq pt2 (polar pt1 0 18.5) )
  (setq pt3 (polar pt1 (/ pi 2) 1.5) )
  (setq pt4 (polar pt2 (/ pi 2) 1.5) )
  (setq pt5 (polar pt3 0 2.5) )
  (setq pt6 (polar pt4 0 -2.5) )
  (command "PLINE" pt5 pt3 "A" pt1 "L" pt2 "A" pt4 "L" pt6 "")
  (text21)
  (text0)
 )
 ;;---------------ve3-------------------------
 (defun ve3 ( / pt1 pt2 pt3 pt4 )
  (setq pt1 (list (+ 10 (car p2)) (+ 2 (cadr p2)) ) )
  (setq pt2 (polar pt1 0 30) )
  (setq pt3 (polar pt1 (/ pi 2) 5) )
  (setq pt4 (polar pt2 (/ pi 2) 5) )
  (command "PLINE" pt1 pt3 pt4 pt2 "")
  (text2)
  (text0)
 )
 ;;---------------ve31-------------------------
 (defun ve31 ( / pt1 pt2 pt3 pt4 )
  (setq pt1 (list (+ 15 (car p2)) (+ 2 (cadr p2)) ) )
  (setq pt2 (polar pt1 0 20) )
  (setq pt3 (polar pt1 (/ pi 2) 5) )
  (setq pt4 (polar pt2 (/ pi 2) 5) )
  (command "PLINE" pt1 pt3 pt4 pt2 "")
  (text21)
  (text0)
 )
 ;;---------------ve4-------------------------
 (defun ve4 ( / pt1 pt3 pt4 )
  (setq pt1 (list (+ 10 (car p2)) (+ 2 (cadr p2)) ) )
  (setq pt3 (polar pt1 (/ pi 2) 5) )
  (setq pt4 (polar pt3 0 30) )
  (command "PLINE" pt1 pt3 pt4 "")
  (text4)
  (text0)
 )
 ;;---------------ve5-------------------------
 (defun ve5 ( / pt1 pt2 pt3 pt5 pt6)
  (setq pt1 (list (+ 15 (car p2)) (+ 2 (cadr p2)) ) )
  (setq pt2 (polar pt1 0 20) )
  (setq pt3 (polar pt1 (/ pi 2) 5) )
  (setq pt5 (polar pt2 (/ pi 2) 7) )
  (setq pt6 (polar pt3 0 22) )
  (command "PLINE" pt6 pt3 pt1 pt2 pt5 "")
  (text5)
  (text0)
 )
 ;;------------------------------------------
; (doi_int)
 (cond
     ( (= 0 style) (ve0) )
     ( (= 1 style) (ve1) )
     ( (= 2 style) (ve2) )
     ( (= 21 style) (ve21) )
     ( (= 3 style) (ve3) )
     ( (= 31 style) (ve31) )
     ( (= 4 style) (ve4) )
     ( (= 5 style) (ve5) )
     (t)
 )
)
;-------------------------------------------
;;;================ Main function  ============================================
   (set_osnap 1)
   (nhap)
   (set_osnap 0)
   (thongke)
   (ve)
   (set_osnap 1)
   (princ)
)
;;;============================================================================
(princ "loaded.")
(princ)
