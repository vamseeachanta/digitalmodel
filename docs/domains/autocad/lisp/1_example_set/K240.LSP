CHUONG TRINH PHU MAT CAU BANG HE KHUNG GOM 240 TAM GIAC
                  DINH TAM GIAC LA KHOI CAU, CANH LA KHOI TRU
            =======================================================




(defun TLKC ()
     (setq r (getint " ban kinh vom cau : "))
     (setq bkcc (getint " ban kinh cau nut : "))
     (setq bktc (getint " ban kinh thanh tru : "))
     (setq T (getpoint " cho tam vom : "))
     
)
(defun ALSLC ()
     (setq a (* 2 (* r (sin (/ pi 10))))
           rn (/ a (* 2 (sin (/ pi 5))))
           m (- r (sqrt (- (* r r) (* rn rn))))
           l (sqrt (+ (* rn rn) (* m m)))
     )
     (setq d (* rn (cos (/ pi 5)))
           xd3 (* d (cos (- (/ pi 2) (/ pi 5))))
           yd3 (* d (cos (/ pi 5)))
           xd2 (* rn (cos (- (/ pi 2) (/ (* 2 pi) 5))))
           yd2 (* rn (cos (/ (* 2 pi) 5)))
     )
     (setq O1 (list (car T) (cadr T) (+ (caddr T) (- r m)))
           S0 (list (car T) (cadr T) (+ (caddr T) r))
           D1 (list (car O1) (- (cadr O1) rn) (caddr O1))
           TT (list (car T) (- (cadr T) r) (caddr T))
           D2 (list (+ (car O1) xd2) (- (cadr O1) yd2) (caddr O1))
           D3 (list (+ (car O1) xd3) (- (cadr O1) yd3) (caddr O1))
     )
)
(defun ATSP ()
   (command "UCS" "O" O1)
        (setq O1t (trans O1 0 1)
              S0t (trans S0 0 1)
              D1t (trans D1 0 1)
              D2t (trans D2 0 1)
              D3t (trans D3 0 1)
         )
         (setq OW1 (polar O1t (* 7 (/ pi 4)) (* rn (sqrt 2)))
               OW2 (polar O1t (* 3 (/ pi 4)) (* rn (sqrt 2)))        
         )
   (command "SPHERE" S0t bkcc)
        (setq sc0 (ssget "L"))
   (command "SPHERE" D1t bkcc)
        (setq sc1 (ssget "L"))
        (setq D11t (polar D1t (+ (/ pi 2) (/ pi 5)) (/ bktc 2))
              D12t (polar D11t (/ pi 5) (* bktc 4))
              D13t (polar D12t (+ (/ pi 2) (/ pi 5)) (/ bktc 2))
              D14t (polar D13t (/ pi 5) (- a (* 8 bktc)))
              D15t (polar D14t (- (/ pi 5) (/ pi 2)) (/ bktc 2))
              D16t (polar D15t (/ pi 5) (* bktc 4))
        )
   (command "PLINE" D1t D11t D12t D13t D14t D15t D16t D2t "C" "")
        (setq splc (ssget "L"))
   (command "REVOLVE" splc "" D2t D1t "")
        (setq st1 (ssget "L"))
   (command "UCS" "W")
   (command "UCS" "3" O1 D1 S0)
        (setq O1u (trans O1 0 1)
              D1u (trans D1 0 1)
              S0u (trans S0 0 1)
        )
        (setq gng (angle D1u S0u))
        (setq D11u (polar D1u (- gng (/ pi 2)) (/ bktc 2))
              D12u (polar D11u gng (* bktc 4))
              D13u (polar D12u (- gng (/ pi 2)) (/ bktc 2))
              D14u (polar D13u gng (- l (* bktc 8)))
              D15u (polar D14u (+ gng (/ pi 2)) (/ bktc 2))
              D16u (polar D15u gng (* bktc 4))
        )
   (command "PLINE" D1u D11u D12u D13u D14u D15u D16u S0u D1u "")
        (setq splt (ssget "L"))
   (command "REVOLVE" splt "" D1u S0u "")
        (setq st2 (ssget "L"))
   (command "UCS" "W")
   (command "UCS" "3" O1 D3 S0)
       (setq D3m (trans D3 0 1)
             S0m (trans S0 0 1)
             O1m (trans O1 0 1)
             Tm (trans T 0 1)
       )
       (setq gd (angle D3m S0m))
       (setq S1m (polar Tm (- gd (/ pi 2)) r))
       (setq dSS (distance S1m S0m))
       (setq gs (angle S1m S0m))
       (setq S1m1 (polar S1m (- gs (/ pi 2)) (/ bktc 2))
             S1m2 (polar S1m1 gs (* bktc 4))
             S1m3 (polar S1m2 (- gs (/ pi 2)) (/ bktc 2))
             S1m4 (polar S1m3 gs (- dSS (* bktc 8)))
             S1m5 (polar S1m4 (+ gs (/ pi 2)) (/ bktc 2))
             S1m6 (polar S1m5 gs (* bktc 4))
       )
   (command "PLINE" S1m S1m1 S1m2 S1m3 S1m4 S1m5 S1m6 S0m S1m "")
       (setq spls (ssget "L"))
   (command "REVOLVE" spls "" S1m S0m "")
       (setq ssds1 (ssget "L"))
   (command "SPHERE" S1m bkcc)
       (setq sc2 (ssget "L"))
       (setq S1 (trans S1m 1 0))
   (command "UCS" "W")
       (command "UCS" "3" D3 D2 S1)
       (setq D3n (trans D3 0 1)
             D2n (trans D2 0 1)
             S1n (trans S1 0 1)
       )
       (setq gd2 (angle D2n S1n))
       (setq dd2 (distance D2n S1n))
       (setq D2n1 (polar D2n (- gd2 (/ pi 2)) (/ bktc 2))
             D2n2 (polar D2n1 gd2 (* bktc 4))
             D2n3 (polar D2n2 (- gd2 (/ pi 2)) (/ bktc 2))
             D2n4 (polar D2n3 gd2 (- dd2 (* bktc 8)))
             D2n5 (polar D2n4 (+ gd2 (/ pi 2)) (/ bktc 2))
             D2n6 (polar D2n5 gd2 (* bktc 4))
       )
   (command "PLINE" D2n D2n1 D2n2 D2n3 D2n4 D2n5 D2n6 S1n D2n "")
       (setq spld (ssget "L"))
   (command "REVOLVE" spld "" S1n D2n "")
       (setq ssdd1 (ssget "L"))
   (command "MIRROR" ssdd1 "" S1n D3n "")
       (setq ssdd2 (ssget "L"))
   (command "UCS" "W")
   (command "UCS" "O" O1)
   (command "ARRAY" sc1 sc2 st1 st2 ssdd1 ssdd2 ssds1 "" "p" O1t 5 "" "")
        (setq sscc1 (ssget "C" OW1 OW2))
   (command "UNION" sscc1 "")
        (setq sscc (ssget "L"))
   (command "UCS" "W")
   (command "UCS" "3" T TT S0)
        (setq Tq (trans T 0 1)
              D1q (trans D1 0 1)
              S0q (trans S0 0 1)
        )
   (command "MIRROR" sscc "" Tq D1q "")
        (setq ssmc (ssget "L"))
   (command "UCS" "W")
   (command "ARRAY" ssmc "" "p" T 5 "" "")
)
(defun MQU ()
   (setq DP1 (polar T (* 8 (/ pi 5)) r)
         DP2 (polar DP1 (/ pi 5) a)
         DP11 (polar DP1 (+ (/ pi 5) (/ pi 2)) (/ bktc 2))
         DP12 (polar DP11 (/ pi 5) (* bktc 4))
         DP13 (polar DP12 (+ (/ pi 5) (/ pi 2)) (/ bktc 2))
         DP14 (polar DP13 (/ pi 5) (- a (* bktc 8)))
         DP15 (polar DP14 (- (/ pi 5) (/ pi 2)) (/ bktc 2))
         DP16 (polar DP15 (/ pi 5) (* bktc 4))
   )
   (command "PLINE" DP1 DP11 DP12 DP13 DP14 DP15 DP16 DP2 DP1 "")
        (setq sph (ssget "L"))
   (command "REVOLVE" sph "" DP1 DP2 "")
        (setq sph1 (ssget "L"))
   (setq D4 (polar DP1 (/ pi 5) (/ a 2)))
   (command "UCS" "3" T D4 S0)
        (setq Te (trans T 0 1)
              D4e (trans D4 0 1)
              S0e (trans S0 0 1)
              D3e (trans D3 0 1)
        )
        (setq gnD4D3 (angle D4e D3e))
        (setq D5e (polar Te (- gnD4D3 (/ pi 2)) r))
        (setq gnD4D5 (angle D4e D5e))
        (setq S2e (polar Te (- gnD4D5 (/ pi 2)) r))
        (setq gnS2D5 (angle S2e D5e))
        (setq S2e1 (polar S2e (- gnS2D5 (/ pi 2)) (/ bktc 2))
              S2e2 (polar S2e1 gnS2D5 (* bktc 4))
              S2e3 (polar S2e2 (- gnS2D5 (/ pi 2)) (/ bktc 2))
              D5e1 (polar D5e (- gnS2D5 (/ pi 2)) (/ bktc 2))
              D5e2 (polar D5e1 (+ gnS2D5 pi) (* bktc 4))
              D5e3 (polar D5e2 (- gnS2D5 (/ pi 2)) (/ bktc 2))
         )
   (command "PLINE" D5e S2e S2e1 S2e2 S2e3 D5e3 D5e2 D5e1 D5e "")
        (setq k1s2 (ssget "L"))
   (command "REVOLVE" k1s2 "" D5e S2e "")
        (setq t1s2 (ssget "L"))
        (setq D5 (trans D5e 1 0)
              S2 (trans S2e 1 0)
        )
   (command "UCS" "W")
   (command "UCS" "3" D4 DP2 D5)
        (setq S2pp (trans S2 0 1)
              D4pp (trans D4 0 1)
              DP1pp (trans DP1 0 1)
              DP2pp (trans DP2 0 1)
              D5pp (trans D5 0 1)
        )
   (command "COPY" t1s2 "" D5pp DP2pp)
        (setq t1s22 (ssget "L"))
   (command "ROTATE" t1s22 "" DP2pp 240)
        (setq t2s2 (ssget "L"))
   (command "MIRROR" t2s2 "" D5pp D4pp "")
        (setq t3s2 (ssget "L"))
   (command "SPHERE" S2pp bkcc)
        (setq sc3 (ssget "L"))
   (command "UCS" "W")
   (command "UCS" "3" T D4 S0)
   (command "MIRROR" t1s2 "" Te D5e "") (setq t1s3 (ssget "L"))
   (command "MIRROR" t2s2 "" Te D5e "") (setq t2s3 (ssget "L"))
   (command "MIRROR" t3s2 "" Te D5e "") (setq t3s3 (ssget "L"))
   (command "MIRROR" sc3 "" Te D5e "") (setq sc4 (ssget "L"))
   (command "UCS" "W")
   (command "ARRAY" sph1 t1s2 t2s2 t3s2 sc3 sc4 t1s3 t2s3 t3s3 "" "p" T 5 "" "")
)
(defun C:K240 ()
              (command "UCS" "W")
              (setvar "OSMODE" 0)
              (setq mc (getstring "cau <C> hay ban cau <B> : "))
       (if (= mc "C") 
           (progn
              (TLKC)        
              (ALSLC)
              (ATSP)
              (MQU)
              (setq dc1 (polar T (* 7 (/ pi 4)) (* r (sqrt 2)))
                    dc2 (polar T (* 3 (/ pi 4)) (* r (sqrt 2)))
              )
              (setq ssnc (ssget "C" dc1 dc2))
              (setq TTT (polar T 0 r))
              (command "UCS" "3" T TTT S0)
              (setq Tc (trans T 0 1)
                    TTTc (trans TTT 0 1)
              )
              (command "MIRROR" ssnc "" Tc TTTc "") 
           )
       )
       (if (= mc "B")
           (progn
              (TLKC)        
              (ALSLC)
              (ATSP)
              (MQU)
           )
       )
       (command "UCS" "W")
)
