(princ "\n         BAN DANG DUNG CHUONG TRINH LISP CUA XAY DUNG                                           WRITE BY VU DUC LUONG - KSXD ")
;DOI MAU VA NET VE
(defun c:1()  
  (prompt "_.change ")
  (princ "\n Change Colour to Red - 1")
  (setq sset (ssget))
  (if (null sset) 
    (progn
      (princ "\nERROR: Nothing selected.")
      (exit)    )  )
  (command "_.change" sset "" "P" "C" "1" "") 
(princ))
(defun c:2()  
  (prompt "_.change ")
  (princ "\n Change Colour to yellow -2 ")
  (setq sset (ssget))
  (if (null sset) 
    (progn
      (princ "\nERROR: Nothing selected.")
      (exit)    )  )
  (command "_.change" sset "" "P" "C" " 2" "") 
(princ))
(defun c:4()  
  (prompt "_.change ")
  (princ "\n Change Colour to green -4")
  (setq sset (ssget))
  (if (null sset) 
    (progn
      (princ "\nERROR: Nothing selected.")
      (exit)    )  )
  (command "_.change" sset "" "P" "C" "4" "") 
(princ))
(defun c:3()  
  (prompt "_.change ")
  (princ "\n Change Colour to cyan -3")
  (setq sset (ssget))
  (if (null sset) 
    (progn
      (princ "\nERROR: Nothing selected.")
      (exit)    )  )
  (command "_.change" sset "" "P" "C" "3" "") 
(princ))
(defun c:5()  
  (prompt "_.change ")
  (princ "\n Change Colour to blue -5")
  (setq sset (ssget))
  (if (null sset) 
    (progn
      (princ "\nERROR: Nothing selected.")
      (exit)    )  )
  (command "_.change" sset "" "P" "C" "5" "") 
(princ))
(defun c:6()  
  (prompt "_.change ")
  (princ "\n Change Colour to magenta -6")
  (setq sset (ssget))
  (if (null sset) 
    (progn
      (princ "\nERROR: Nothing selected.")
      (exit)    )  )
  (command "_.change" sset "" "P" "C" "6" "") 
(princ))
(defun c:7()  
  (prompt "_.change ")
  (princ "\n Change Colour to white -7")
  (setq sset (ssget))
  (if (null sset) 
    (progn
      (princ "\nERROR: Nothing selected.")
      (exit)    )  )
  (command "_.change" sset "" "P" "C" "7" "") 
(princ))
(defun c:8()  
  (prompt "_.change ")
  (princ "\n Change Colour to 8 -8")
  (setq sset (ssget))
  (if (null sset) 
    (progn
      (princ "\nERROR: Nothing selected.")
      (exit)    )  )
  (command "_.change" sset "" "P" "C" "8" "") 
(princ))
(defun c:9 ()
(setq ss (ssget))
(command "chprop" ss "" "c" "9" ""))
(defun c:10 ()
(setq ss (ssget))
(command "chprop" ss "" "c" "10" ""))
(defun c:11()  
  (prompt "_.change")
  (princ "\n Change Lineptype to Hidden")
  (setq sset (ssget))
  (if (null sset) 
    (progn
      (princ "\nERROR: Nothing selected.")
      (exit)    )  )
  (command "_.change" sset "" "P" "LT" "Hidden" "") 
(princ))
;DAT KHO GIAY BAN VE
(Defun c:a4 ()
	(setq mv_sc 100);Ti le  ban ve
      (setq x4  297)
      (setq y4  210)
  (setq x4 (* mv_sc x4) 
        y4 (* mv_sc y4)  )
  (command  
    "LIMITS" "0,0" (list x4 y4)
    "PLINE" "0,0" (list 0 y4) (list x4 y4) (list x4 0) "0,0" "_C"
    "RECTANG" "2500,500" "@26700,20000"
    "ZOOM" "_a"  ))
; Ban Ve A3
(Defun c:a3 ()
	(setq mv_sc 100)
      (setq x3  420)
      (setq y3  297)
  (setq x3 (* mv_sc x3) 
        y3 (* mv_sc y3)  )
  (command  
    "LIMITS" "0,0" (list x3 y3)
    "PLINE" "0,0" (list 0 y3) (list x3 y3) (list x3 0) "0,0" "_C"
    "RECTANG" "2500,500" "@39000,28700"
    "ZOOM" "_a"  ))
(Defun c:a2 ()
	(setq mv_sc 100)
      (setq x2  594)
      (setq y2  420)
  (setq x2 (* mv_sc x2) 
        y2 (* mv_sc y2)  )
  (command  
    "LIMITS" "0,0" (list x2 y2)
    "PLINE" "0,0" (list 0 y2) (list x2 y2) (list x2 0) "0,0" "_C"
    "RECTANG" "2500,500" "@56400,41000"
    "ZOOM" "_a"  ))
(Defun c:a1 ()
	(setq mv_sc 100)
      (setq x1  840)
      (setq y1  594)
  (setq x1 (* mv_sc x1) 
        y1 (* mv_sc y1)  )
  (command  
    "LIMITS" "0,0" (list x1 y1)
    "PLINE" "0,0" (list 0 y1) (list x1 y1) (list x1 0) "0,0" "_C"
    "RECTANG" "2500,500" "@81000,58400"
    "ZOOM" "_a"  ))
(Defun c:a0 ()
	(setq mv_sc 100)
      (setq x0  1188)
      (setq y0  840)
  (setq x0 (* mv_sc x0) 
        y0 (* mv_sc y0)  )
  (command  
    "LIMITS" "0,0" (list x0 y0)
    "PLINE" "0,0" (list 0 y0) (list x0 y0) (list x0 0) "0,0" "_C"
    "RECTANG" "2500,500" "@115800,83000"
    "ZOOM" "_a"  ))
;HIEU CHINH KICH THUOC
(DEFUN C:CD (/ CMD SS LTH DEM PT DS KDL N70 GOCX GOCY PT13 PT14 PTI PT13I PT14I
                PT13N PT14N O13 O14 N13 N14 OSM OLDERR PT10 PT11)
(SETQ CMD (GETVAR "CMDECHO"))
(SETQ OSM (GETVAR "OSMODE"))
(SETQ OLDERR *error*
      *error* myerror)
(PRINC "Please select dimension object!")
(SETQ SS (SSGET))
(SETVAR "CMDECHO" 0)
(SETQ PT (GETPOINT "Point to trim or extend:"))
(SETQ PT (TRANS PT 1 0))
(COMMAND "UCS" "W")
(SETQ LTH (SSLENGTH SS))
(SETQ DEM 0)
(WHILE (< DEM LTH)
    (PROGN
	(SETQ DS (ENTGET (SSNAME SS DEM)))
	(SETQ KDL (CDR (ASSOC 0 DS)))
	(IF (= "DIMENSION" KDL)
	   (PROGN
		(SETQ PT10 (CDR (ASSOC 10 DS)))
		(SETQ PT11 (CDR (ASSOC 11 DS)))
		(SETQ PT13 (CDR (ASSOC 13 DS)))
		(SETQ PT14 (CDR (ASSOC 14 DS)))
		(SETQ N70 (CDR (ASSOC 70 DS)))
		(IF (OR (= N70 32) (= N70 33) (= N70 160) (= N70 161))
		   (PROGN
			(SETQ GOCY (ANGLE PT10 PT14))
			(SETQ GOCX (+ GOCY (/ PI 2)))
		   )
		)
		(SETVAR "OSMODE" 0)
		(SETQ PTI (POLAR PT GOCX 2))
		(SETQ PT13I (POLAR PT13 GOCY 2))
		(SETQ PT14I (POLAR PT14 GOCY 2))
		(SETQ PT13N (INTERS PT PTI PT13 PT13I NIL))
		(SETQ PT14N (INTERS PT PTI PT14 PT14I NIL))
		(SETQ O13 (ASSOC 13 DS))
		(SETQ O14 (ASSOC 14 DS))
		(SETQ N13 (CONS 13 PT13N))
		(SETQ N14 (CONS 14 PT14N))
		(SETQ DS (SUBST N13 O13 DS))
		(SETQ DS (SUBST N14 O14 DS))
		(ENTMOD DS)
	   )
	)
	(SETQ DEM (+ DEM 1))
    )
)
(COMMAND "UCS" "P")
(SETVAR "CMDECHO" CMD)
(SETVAR "OSMODE" OSM)
(setq *error* OLDERR)               ; Restore old *error* handler
(PRINC)
)
;******************************************************************************

(DEFUN C:BD (/ CMD SS LTH DEM PT DS KDL N70 GOCX GOCY PT13 PT14 PTI
                PT10 PT10I PT10N O10 N10 PT11 PT11N O11 N11 KC OSM OLDERR)
(SETQ CMD (GETVAR "CMDECHO"))
(SETQ OSM (GETVAR "OSMODE"))
(SETQ OLDERR *error*
      *error* myerror)
(PRINC "Please select dimension object!")
(SETQ SS (SSGET))
(SETVAR "CMDECHO" 0)
(SETQ PT (GETPOINT "Point to trim or extend:"))
(SETQ PT (TRANS PT 1 0))
(COMMAND "UCS" "W")
(SETQ LTH (SSLENGTH SS))
(SETQ DEM 0)
(WHILE (< DEM LTH)
    (PROGN
	(SETQ DS (ENTGET (SSNAME SS DEM)))
	(SETQ KDL (CDR (ASSOC 0 DS)))
	(IF (= "DIMENSION" KDL)
	   (PROGN
		(SETQ PT13 (CDR (ASSOC 13 DS)))
		(SETQ PT14 (CDR (ASSOC 14 DS)))
		(SETQ PT10 (CDR (ASSOC 10 DS)))
		(SETQ PT11 (CDR (ASSOC 11 DS)))
		(SETQ N70 (CDR (ASSOC 70 DS)))
		(IF (OR (= N70 32) (= N70 33) (= N70 160) (= N70 161))
		   (PROGN
			(SETQ GOCY (ANGLE PT10 PT14))
			(SETQ GOCX (+ GOCY (/ PI 2)))
		   )
		)
		(SETVAR "OSMODE" 0)
		(SETQ PTI (POLAR PT GOCX 2))
		(SETQ PT10I (POLAR PT10 GOCY 2))
		(SETQ PT10N (INTERS PT PTI PT10 PT10I NIL))
		(SETQ KC (DISTANCE PT10 PT10N))
		(SETQ O10 (ASSOC 10 DS))
		(SETQ N10 (CONS 10 PT10N))
		(SETQ DS (SUBST N10 O10 DS))
		(SETQ PT11N (POLAR PT11 (ANGLE PT10 PT10N) KC))
		(SETQ O11 (ASSOC 11 DS))
		(SETQ N11 (CONS 11 PT11N))
		(SETQ DS (SUBST N11 O11 DS))
		(ENTMOD DS)
	   )
	)
	(SETQ DEM (+ DEM 1))
    )
)
(COMMAND "UCS" "P")
(SETVAR "CMDECHO" CMD)
(SETVAR "OSMODE" OSM)
(setq *error* OLDERR)
(PRINC)
)
;ZOOM
(defun c:zz ()  (command "'.zoom" "p"))
(defun c:zzz ()  (command "'.zoom" "p"))
(defun c:zw ()  (command "'.zoom" "w"))
(defun c:ze ()  (command "'.zoom" "e"))
(defun c:za ()  (command "'.zoom" "a"))
(defun c:zd ()  (command "'.zoom" "d"))
;PLINE
(defun c:pl () (command "pline"))
(defun c:, () (command "osnap"  "")
(command "osnap" "End,Mid,Cen,Quad,Int,Perp,Tan,Near,App,Int,Ext,Par"  ))
(defun c:pe () (command "pedit"))
(defun c:pa () (command "pline" pause "a"))
(defun c:pj () (command "pedit" pause "j"))
(defun c:pw () (command "pedit" pause "w"))
(defun c:lty () (command "linetype"))
(defun c:lts () (command "ltscale"))
(defun c:tri () (command "polygon" "3" pause "i"))
(defun c:sqi () (command "polygon" "4" pause "i"))
;CHAMFER
(defun c:cf () (command "chamfer"))
(defun c:cfd () (command "chamfer" "d"))
;FILLET
(defun c:f () (command "fillet"))
(defun c:fr () (command "fillet" "r"))
;BREAK
(defun c:br () (command "break"))
(defun c:bf () (command "break" pause "f"))
;COPY
(defun c:c () (command "copy"))
(defun c:cX () (ssget) (command "copy" "p" "" "m"))
(defun c:cz (/ A B C D)
  (setvar "CMDECHO" 0)
  (prompt "\nFor rotated copy")
  (ssget)
  (setq A (getpoint "\nBase point: "))
  (command "ID" A)
  (setq B (getpoint "\nNew point <Return> if same as Base point> "))
  (if (= B nil) (setq B A))

  (command "COPY" "P" "" A A)
  (command "MOVE" "P" "" A B)
  (command "ROTATE" "P" "" B pause)
  (setvar "CMDECHO" 1)
)
;COP THONG MINH
(defun xulytext (text / kytu ma sokt luusokt lui )
(setq 	kytu	(substr text (strlen text))
		ma	(ascii kytu)
		sokt	(read kytu) 
		lui	1
)
(if (numberp sokt)
		(progn
			(setq luusokt	(1+ sokt))
			(if (and 	(numberp sokt) 
					(> (strlen text) 1)
			    )	
			   (progn
				(setq 	kytu	(substr text (1- (strlen text)))
						sokt	(read kytu) 
										)
				(if 	(numberp sokt) 
					(setq luusokt (1+	sokt)
							lui 	2

						)
				)
			    );progn	
			)
			(if (= luusokt	100)	(setq 	luusokt	0))
			(setq 	kytu		(rtos luusokt 2 0)
					
					text	(strcat	(substr text 1 (- (strlen text) lui))  kytu)
			)
		);progn			 
		(if   (or 	(= kytu "z")
				(= kytu "Z")
			)
			(setq 	text		(strcat 	text	"0")
				textxl		"0"
			)
			(setq		ma	(1+	ma)
					text	(strcat	(substr text 1 (1- (strlen text)))  (chr ma))
			)
		);if
);if
)
;*********************************************************************
(defun doitext(tendoituong / chuoi doituong thoat tam dsach kieu text vitri10 vitri11 dem canle)
;Neu doi tuong la text thi tiep tuc
(setq 	doituong 	(entget  tendoituong)
	kieu		(cdr (assoc 	0	doituong))
	canle		(cdr (assoc 	72	doituong))
)	
(if (or (= kieu		"TEXT")
	(= kieu 	"MTEXT")	
    ) 	
	(progn
		(setq	textxl	(xulytext textxl)
			text	(cons 1 textxl)
			vitri10 	(cdr (assoc 10 doituong))
			vitri10 	(list (+ (car vitri10) (car vitrilech)) (+ (nth 1 vitri10) (nth 1 vitrilech)))
			vitri10		(cons 10 vitri10)
			vitri11 	(cdr (assoc 11 doituong))
			vitri11 	(list (+ (car vitri11) (car vitrilech)) (+ (nth 1 vitri11) (nth 1 vitrilech)))
			vitri11		(cons 11 vitri11)
			dem	0
			dsach	nil
		)
		(foreach tam 	doituong
			(cond
				((= (car tam)	1)	(setq dsach 	(append dsach (list text))))
				((= (car tam)	10)	(setq dsach 	(append dsach (list vitri10))))
				((= (car tam)	11)	(setq dsach 	(append dsach (list vitri11))))
				((setq dsach 	(append dsach (list tam))))
			)
		)
		(entmake dsach)
	);progn
);if
	);

;sao doi tuong cu sang vi tri moi

(defun copy_dt (tendoituong )
(command "copy" tendoituong "" goc toi )
);defun

(defun c:CV ( / cumdt dodai thoat dem ten doituong textxl dem goc toi)
; Khoi dau cua chuong trinh
(princ "\nCopy Inteligent...\n")
(setq 	luuecho	(getvar	"cmdecho")
	luu	*error*
	*error*	ketthuc
	cumdt 	(ssget)
	dodai 	(sslength cumdt)
	goc		(getpoint "\nSelect base point:")
	thoat		nil
	dem		0
	textxl		nil
);
(setvar "cmdecho" 0)
; Loc ra duoc ong text de xu ly
(while	(and 	(= thoat	nil)
		(< dem	dodai)
	)
	(setq 	ten	(ssname cumdt dem)
		dem	(1+ 	dem)
		doituong (entget ten)
		kieu	 (cdr (assoc 	0	doituong))			
	)
	
	(if (or (= kieu		"TEXT")
		(= kieu 	"MTEXT")	
    	    )
		(setq 	thoat	T
			textxl 	(cdr (assoc 1 doituong)) 	
		)
	)
);
(while T 
(setq	toi		(getpoint "\nSelect next point: " goc)
	vitrilech 	(list 	(- (car toi) (car goc)) (- (nth 1 toi) (nth 1 goc)))
	dem		0
)
(while	(< dem dodai)
	(setq 	ten	(ssname cumdt dem)
		dem	(1+ 	dem)
		doituong (entget ten)
		kieu	 (cdr (assoc 	0	doituong))			
	)

	(if (or (= kieu		"TEXT")
		(= kieu 	"MTEXT")	
    	    )
		(doitext	ten)
		(copy_dt	ten)

	);if
)
);while
(ketthuc)
)
;ARRAY
(defun c:aq () (command "array"))
(defun c:arp () (ssget) (command "array" "p" "" "p"))
(defun c:arr () (ssget) (command "array" "p" "" "r"))
;TRIM
(defun c:t () (command "trim"))
(defun c:tf () (ssget) (command "trim" "p" "" "f"))
;EXTEND
(defun c:ee () (command "extend"))
(defun c:ef () (ssget) (command "extend" "p" "" "f"))
;DIM
(defun c:da () 
(command "layer" "m" "dim" "c" "150" """")
(command "dim" "ali"))
(defun c:dl () 
(command "layer" "m" "dim" "c" "150" """")
(command "dim" "lead" ))
(defun c:du () 
(command "layer" "m" "dim" "c" "150" """")
(command "dim" "up" ))
(defun c:dv () 
(command "layer" "m" "dim" "c" "150" """")
(command "dim" "ver" ))
(defun c:dn () 
(command "layer" "m" "dim" "c" "150" """")
(command "dim" "new" ))
(defun c:dh () 
(command "layer" "m" "dim" "c" "150" """")
(command "dim" "hor" ))
(defun c:das () 
(command "layer" "m" "dim" "c" "150" """")
(command "dim" "dimasz" "0.10" "exit"))
;LAYER
(defun c:la () (command "layer"))
(defun c:lm () (command "layer" "m"))
(defun c:lt () (command "layer" "t"))
(defun c:lf () (command "layer" "f"))
(defun c:ln () (command "layer" "n"))
(defun c:lc () (command "layer" "c"))
(defun c:las () (command "layer" "t" pause "s" pause "f" pause ""))
(defun c:lof () (command "layer" "off"))
(defun c:lon () (command "layer" "on"))
;BLOCK
(defun c:bl () 
(command "layer" "m" "NOITHAT" "c" "154" """")
(command "block"))
(defun c:Bh () 
(command "layer" "m" "hatch" "c" "251" """")
(command "BHATCH"))
(defun c:in () (command "insert"))
;TEXT
(defun c:dt () 
(command "layer" "m" "text" "c" "84" """")
(command "dtext"))
(defun c:de () (command "ddedit"))
(defun c:st () (command "style"))
;ATTRIB
(defun c:as () (command "attedit" "" "" "" "" pause "" "s"))
(defun c:ah () (command "attedit" "" "" "" "" pause "" "h"))
(defun c:ast () (command "attedit" "" "" "" "" "auto" "" "s"))
(defun c:avc () (command "attedit" "" "" "" "" pause "" "v" "c"))
(defun c:avr () (command "attedit" "" "" "" "" pause "" "v" "r"))
(defun c:div () (command "divide"))
(defun c:ex () (command "explode"))
(defun c:ep () (command "explode"))
(defun c:lim () (command "limits"))
(defun c:li () (command "list"))
(defun c:m () (command "move"))
(defun c:mm () (command "mirror"))
(defun c:mi () (command "mirror"))
(defun c:o () (command "offset"))
(defun c:po () (command "polygon"))
(defun c:ro () (command "rotate"))
(defun c:rr () (command "rotate"))
(defun c:s () (command "stretch" "c"))
(defun c:so () (command "solid"))
(defun c:sc () (command "scale"))
(defun c:sn () (command "snap"))
(defun c:v () (command "view"))
(defun c:aw () (command "appload"))
(defun c:lf (/ ee23 xx23)
   (setvar "cmdecho" 0)
   (setq ee23 (car (entsel "\nPick Object on desired layer: ")))
   (if ee23 (progn
             (setq ee23 (entget ee23))
             (setq xx23 (cdr (assoc 8 ee23)))
             (command "layer" "f" xx23 "")
          )
    )
   (prompt (strcat  xx23 "\n is now freezed."))
   (setvar "cmdecho" 1)
   (princ)
)
(DEFUN C:ED  () (COMMAND "DIM1" "NEWTEXT"))
(DEFUN C:D   () (COMMAND "DIST"))
(defun c:aa  () (command "area"))
(DEFUN C:DJ  () (COMMAND "dtext" "J" ))
(DEFUN C:Df  () 
(command "layer" "m" "dim" "c" "150" """")
(COMMAND "DIMLINEAR"))
(DEFUN C:LE  () (COMMAND "DIM1" "LEA"))
(DEFUN C:TT  () (COMMAND "TRIM" "ALL" ""))
(DEFUN C:VRS () (COMMAND "VIEWRES" "Y" "2000"))
(DEFUN C:Q  () (COMMAND "QSAVE"))
(defun c:180 () (command "rotate" pause "" "@""180"))
(defun c:-180 () (command "rotate" pause "" "@""-180"))
(defun c:90 () (command "rotate" pause "" "@""90"))
(defun c:-90 () (command "rotate" pause "" "@" "-90"))
(defun c:45 () (command "rotate" pause "" "@" "45"))
(defun c:-45 () (command "rotate" pause "" "@" "-45"))
(defun c:30 () (command "rotate" pause "" "@" "30"))
(defun c:-30 () (command "rotate" pause "" "@" "-30"))
(defun c:60 () (command "rotate" pause "" "@" "60"))
(defun c:-60 () (command "rotate" pause "" "@" "-60"))
(defun c:r90 (/ ss1)
  (setq ss1 (ssget))(command "rotate" ss1 "" pause "90"))
(defun c:r-90 (/ ss1)
  (setq ss1 (ssget))(command "rotate" ss1 "" pause "-90"))
(defun c:r45 (/ ss1)
  (setq ss1 (ssget))(command "rotate" ss1 "" pause "45"))
(defun c:r-45 (/ ss1)
  (setq ss1 (ssget))(command "rotate" ss1 "" pause "-45"))
(defun c:r30 (/ ss1)
  (setq ss1 (ssget))(command "rotate" ss1 "" pause "30"))
(defun c:r-30 (/ ss1)
  (setq ss1 (ssget))(command "rotate" ss1 "" pause "-30"))
(defun c:r60 (/ ss1)
  (setq ss1 (ssget))(command "rotate" ss1 "" pause "60"))
(defun c:r-60 (/ ss1)
  (setq ss1 (ssget))(command "rotate" ss1 "" pause "-60"))
(defun c:r180 (/ ss1)
  (setq ss1 (ssget))(command "rotate" ss1 "" pause "180"))
(defun c:r-180 (/ ss1)
  (setq ss1 (ssget))(command "rotate" ss1 "" pause "-180"))
; DOI CHU HOA <-->THUONG
(defun C:DOI (/ x c e ss txt cmde)
  (setq cmde (getvar "CMDECHO"))
  (setvar "CMDECHO" 0)
  ; List keywords
  (initget "HOA Thuong")
  (setq x (getkword "\nChange case to? Thuong/<HOA>: "))
  ; Create a selection set of entities
  (setq ss (ssget))
  ; Initialise counter
  (setq c 0)
  (if ss (setq e (ssname ss c)))
  (while e
    (setq e (entget e))
    ; Ensure entity is text
    (if (= (cdr (assoc 0 e)) "TEXT")
        (progn
           (if (= x "Thuong")
                 ; Option to convert to thuong case
                 (setq txt (strcase (cdr (assoc 1 e)) t))
                 ; Option to convert to hoa case
                 (setq txt (strcase (cdr (assoc 1 e))))
           )
           (setq e (subst (cons 1 txt) (assoc 1 e) e))
           (entmod e)
        )
    )
    (setq c (1+ c)) ; Increment counter.
    (setq e (ssname ss c))  ; Obtain next entity.
   )
   (setvar "CMDECHO" cmde)
   (princ)
)
;TAT LAYER
(DEFUN C:LK (/ SSET SSL ENT LAY I MODE)
   (SETQ SSET (SSGET))
   (IF (/= NIL SSET) 
    (PROGN
     (SETQ SSL (SSLENGTH SSET))
     (SETQ LAY "")
     (SETQ I 0)
     (SETQ MODE 0) 
     (WHILE (< I SSL)
       	  (SETQ ENT (ENTGET (SSNAME SSET I)))
	  (IF (= (CDR (ASSOC '8 ENT)) (GETVAR "CLAYER")) (SETQ MODE 1) )
          (SETQ LAY (STRCAT LAY "," (CDR (ASSOC '8 ENT)) ))
          (SETQ I (+ I 1))
     )
     (COMMAND "LAYER" "LOCK" LAY "")
     (IF (= MODE 1) (COMMAND "") )
    )
   )
   (PRINC)
)
;MO LAYER
(DEFUN C:ULK (/ SSET SSL ENT LAY I MODE)
   (SETQ SSET (SSGET))
   (IF (/= NIL SSET) 
    (PROGN
     (SETQ SSL (SSLENGTH SSET))
     (SETQ LAY "")
     (SETQ I 0)
     (SETQ MODE 0) 
     (WHILE (< I SSL)
       	  (SETQ ENT (ENTGET (SSNAME SSET I)))
	  (IF (= (CDR (ASSOC '8 ENT)) (GETVAR "CLAYER")) (SETQ MODE 1) )
          (SETQ LAY (STRCAT LAY "," (CDR (ASSOC '8 ENT)) ))
          (SETQ I (+ I 1))
     )
     (COMMAND "LAYER" "UNLOCK" LAY "")
     (IF (= MODE 1) (COMMAND "") )
    )
   )
   (PRINC)
)
;KY HIEU DOI XUNG
(DEFUN C:CO (/ CMD OSM OLDERR PT1 PT2 PT3 PT4 PT5 PT6 PT7 PT8 PT9
		SZ G45 G135 G90 G180 SS loi)
(defun loi (s)
 (if (= s "Function cancelled")
     (princ)
     (princ (strcat "Error:" s))
 )
 	(SETVAR "CMDECHO" CMD)
 	(SETVAR "OSMODE" OSM)
	(SETQ *error* OLDERR)
 	(PRINC)
)
;;***************************************
 (SETQ CMD (GETVAR "CMDECHO"))
 (SETQ OSM (GETVAR "OSMODE"))
 (SETVAR "CMDECHO" 0)
 (SETQ OLDERR *error*
	*error* loi)
 (SETQ SZ (GETREAL "Size <1>:"))
 (IF (= SZ nil) (SETQ SZ 100))
 (SETQ G45 (/ PI 4))
 (SETQ G135 (* 3 (/ PI 4)))
 (SETQ G90 (- G45 (/ PI 2)))
 (SETQ G180 (+ G135 (/ PI 2)))
 (SETQ PT1 (GETPOINT "\nDiem doi xung:"))
 (SETVAR "OSMODE" 0)
 (SETQ PT2 (POLAR PT1 G45 (* 2 SZ)))
 (SETQ PT3 (POLAR PT2 G90 (* 2 SZ)))
 (SETQ PT4 (POLAR PT1 G45 (* 1 SZ)))
 (SETQ PT5 (POLAR PT1 G135 (* 2 SZ)))
 (SETQ PT6 (POLAR PT5 G180 (* 2 SZ)))
 (SETQ PT7 (POLAR PT1 G135 (* 1 SZ)))
 (SETQ PT8 (POLAR PT1 G45 (* -0.7 SZ)))
 (SETQ PT9 (POLAR PT1 G135 (* -0.7 SZ)))
 (PRINC "\nGoc quay:")
 (SETQ SS (SSADD))
(command "layer" "m" "ghichu" "c" "150" """")
(COMMAND "COLOR" "150" "")
 (COMMAND "LINE" PT8 PT2 "")
 (SETQ SS (SSADD (ENTLAST) SS))
 (COMMAND "LINE" PT9 PT5 "")
 (SETQ SS (SSADD (ENTLAST) SS))
(COMMAND "COLOR" "7" "")
 (COMMAND "SOLID" PT2 PT3 PT4 "" "")
 (SETQ SS (SSADD (ENTLAST) SS))
 (COMMAND "SOLID" PT5 PT6 PT7 "" "")
 (SETQ SS (SSADD (ENTLAST) SS))
 (COMMAND "ROTATE" SS "" PT1 PAUSE)
(COMMAND "COLOR" "BYLAYER" "")
 (SETVAR "CMDECHO" CMD)
 (SETVAR "OSMODE" OSM)
 (SETQ *error* OLDERR)
 (PRINC)
)
;chuyen sang layer hien hanh
(defun c:Cl (/ va)
 (setvar "cmdecho" 0)
 (setq va (cdr (assoc 8 (entget
                         (car (entsel "Chon doi tuong de doi layer hien hanh: "))))))
 (command "layer" "set" va "")
)
(Vmon)

(Defun TC (pt newstr)
  (setq oldob (entget (ssname (ssget pt) 0)) txtstr (assoc 1 oldob))
  (entmod (subst (cons 1 newstr) txtstr oldob))
)

(defun c:AP () (command "APPLOAD"))
(defun c:CC () (command "CIRCLE"))
(defun c:EE () (command "EXTEND"))
(defun c:MM () (command "MIRROR"))
(defun c:R () (command "RECTANG"))
(defun c:dc () (command "DIMCONTINUE"))
(defun c:dg () (command "DIMANGULAR"))
(defun c:dd () (command "DIMRADIUS"))
(defun c:mk () (command "COLOR"))
(defun c:ii () (command "INSERT"))
(defun c:bb () (command "BLOCK"))
(defun c:MN () (command "MATCHPROP"))
(defun c:UU () (command "UCS"))
(defun c:LLL () (command "LTSCALE"))
(defun c:rr () (command "rotate" "au")(princ))	
(defun taolop (mau lop / a) (setq a (tblsearch "layer" lop))
 (if (null a) (command "layer" "n" lop "c" mau lop "")) (setvar "clayer" lop)
 (princ "\n  Layer_ hien hanh la:  ") (princ lop) (princ) )
(DEFUN C:LTHEP  () (taolop 6    "Thep") )
(DEFUN C:LTEXT  () (taolop 84    "TEXT") )
(DEFUN TIM () (taolop 24 "TIM") (command "layer" "lt" "dashdot" "tim" ""))
(DEFUN C:LMANH () (taolop 163 "MANH")) 
(defun c:LTIM () (tim))
(DEFUN khuat () (taolop 163 "KHUAT") (command "layer" "lt" "hidden" "khuat" ""))
(defun c:LKHUAT () (khuat))
(DEFUN C:LDIM  () (taolop  8    "DIM") )
(DEFUN C:Lcua () (taolop 44    "CUA") )
(DEFUN C:LTUONG () (taolop 31    "TUONG") )
(DEFUN C:Lnthat () (taolop 154    "NOITHAT") )
(DEFUN C:LDAM  () (taolop 3    "DAM") )
(DEFUN C:Lgchu  () (taolop 150    "GHICHU") )
(DEFUN C:LCAT  () (taolop 31    "CAT") )
(DEFUN C:LHATCH  () (taolop 251    "HATCH") )
(DEFUN C:LKCAU  () (taolop 7    "KETCAU") )
(DEFUN C:LTHAY  () (taolop 4    "THAY") )
(defun c:pw (/ pl23 wi43)
   (setq pl23 (car (entsel "\nChon polyline: ")))
   (setq wi43 (getstring "\nDo rong moi : "))
   (command "pedit" pl23 "w" wi43 "")(princ)
)
(DEFUN C:LP(/ SSET NET SSL M)
   (PRINC "\nChon duong thang :")
   (SETQ SSET (SSGET))
   (IF (/= NIL SSET) (PROGN
   (SETQ SSL (SSLENGTH SSET))
   (INITGET 4)
   (SETQ NET (GETREAL "Do rong moi : "))
   (IF (/= NIL NET)
    (WHILE (> SSL 0)
      (SETQ M (SSNAME SSET (SETQ SSL (- SSL 1)) ))
      (IF (= (CDR (ASSOC '0 (ENTGET M))) "LINE") 
          (COMMAND "PEDIT" M "Y" "W" NET "") 
      ) 
    ) 
   )))
   (PRINC)
) 
 (defun c:mv () (command "pedit" pause "e" "m" pause "n" "m" pause "x" ""))
(defun c:len ()  (command "lengthen" "de"))
(defun c:io () (command "multiple")(princ))


;;; ----------------------- TRIM NHIEU DOI TUONG -------------------------
(Defun C:TR ()  (Setq CVAR (Getvar "CMDECHO"))  (Setvar "CMDECHO" 0)
  (Prompt "Select cutting edges :")  (Setq CUTEDG (Ssget))
  (Prompt "Select objects to trim :")  (Setq SS (SSget))
  (Setq LEN (SSlength SS))  (Setq I -1)
  (Setq SIDE (getpoint"pick side to trim"))  (Command "TRIM" CUTEDG "")
  (Repeat LEN
   (Setq I (1+ I))
   (Command (List(SSname SS I) SIDE))  )  (Command "")
  (Setvar "CMDECHO" CVAR)  (Princ "\nTrim complete.")  (Princ) )

;;;====================== EXTEND NHIEU DOI TUONG ===========================
(Defun C:Ex ()
  (Setq CVAR (Getvar "CMDECHO"))  (Setvar "CMDECHO" 0)
  (Prompt "Chon doi tuong dich cua EXTEND :")  (Setq CUTEDG (Ssget))
  (Prompt "Chon doi tuong de Extend :")  (Setq SS (SSget))  (Setq LEN (SSlength SS))
  (Setq I -1)
  (Setq SIDE (getpoint"Chon phia de EXTEND"))  (Command "EXTEND" CUTEDG "")
  (Repeat LEN
   (Setq I (1+ I))
   (Command (List(SSname SS I) SIDE))  )  (Command "")
  (Setvar "CMDECHO" CVAR)  (Princ "Da Extend xong moi ban lam tiep")  (Princ) )

;;; ===============  EXTEND 1 DOI TUONG THEO KHOANG CACH ===============
(defun c:EEx ()  (setq os (getvar "osmode"))  (setvar "osmode" 512)
  (setq pt1 (getpoint "\nKich vao 1 dau doan thang can EXTEND  "))
  (setvar "osmode" os)
  (setq dis (getdist pt1 "\nKhoang cach can EXTEND :"))
  (command "circle" "endpoint" pt1 dis)  (command "extend" "last" "" pt1 "")  (command "erase" "last" "") (princ))

(defun c:uw () (command "ucs" "w" "plan" ""))
(defun c:uv () (command "ucs" "v"))
(defun c:q () (command "properties"))

(defun c:15 () (command "ucs" "z" 15))
(defun c:30 () (command "ucs" "z" 30))
(defun c:45 () (command "ucs" "z" 45))
(defun c:60 () (command "ucs" "z" 60))
(defun c:75 () (command "ucs" "z" 75))
(defun c:90 () (command "ucs" "z" 90))

(defun c:-15 () (command "ucs" "z" -15))
(defun c:-30 () (command "ucs" "z" -30))
(defun c:-45 () (command "ucs" "z" -45))
(defun c:-60 () (command "ucs" "z" -60))
(defun c:-75 () (command "ucs" "z" -75))
(defun c:-90 () (command "ucs" "z" -90))


;;; =========================== Layer hien hanh =============================
(defun layset (/ LAY) (setvar "cmdecho" 0)
 (setq LAY (entsel "\nChon doi tuong cho Layer hien hanh : "))
 (if LAY     (progn     
  (setq LAY (cdr (assoc 8 (entget (car LAY)))))
  (command "_.layer" "set" LAY "") (princ (strcat "\nLayer : " LAY " da la hien hanh."))  )
             (progn
      (if (not ddlop) (load "ddlop"))  (if (setq LAY (ddlop)) 
             (progn
            (command "_.LAYER" "ON" LAY "THAW" LAY "SET" LAY "")  (princ (strcat "\nLayer : " LAY " da la hien hanh.")) ) ) ) )(princ) )
(defun c:cg     () (layset))

;;; ================== Cap nhat doi tuong vao layer hien hanh ==================
(Defun LAYCUR (/ SS CNT LAY)  (setvar "cmdecho" 0)
  (if (not (setq SS (ssget "i")))
    (progn (prompt "\nChon doi tuong gan vao layer hien hanh: ")
      (setq SS (ssget))    )  )
  (if SS    (progn
   (setq CNT (sslength SS)) (princ (strcat "\n" (itoa CNT) " doi tuong tim thay."))                  (command "_.move" SS "")                      
      (if (> (getvar "cmdactive") 0)                
        (progn
          (command "0,0" "0,0") (setq SS  (ssget "p") CNT (- CNT (sslength SS))    )   )
          (setq SS nil)     )  (if (> CNT 0)                                 
          (princ (strcat "\n" (itoa CNT) " doi tuong tren layer LOCK.")) ) ) )
  (if SS    (progn
      (setq LAY (getvar "CLAYER")) (command "_.chprop" SS "" "_la" LAY "")
      (if (= (sslength SS) 1)
        (prompt (strcat "\n1 doi tuong da cap nhat vao layer : " LAY " (layer hien hanh)."))
        (prompt (strcat "\n" (itoa (sslength SS)) " doi tuong da cap nhat vao layer : " LAY " (layer hien hanh).")) ) ))  (princ) );end
(defun c:Lm () (laycur)) 

;;; =========================== Layer Iso ===================================
(Defun LAYISO (/ SS CNT LAY LAYLST VAL)  (setvar "cmdecho" 0)
  (if (not (setq SS (ssget "i")))    (progn
      (prompt "\nChon doi tuong cho layer muon hien: ")
      (setq SS (ssget))    )  )
  (if SS    (progn      (setq CNT 0)
      (while (setq LAY (ssname SS CNT))
        (setq LAY (cdr (assoc 8 (entget LAY))))
        (if (not (member LAY LAYLST))
          (setq LAYLST (cons LAY LAYLST))        )
        (setq CNT (1+ CNT))      )
      (if (member (getvar "CLAYER") LAYLST)
        (setq LAY (getvar "CLAYER"))
        (setvar "CLAYER" (setq LAY (last LAYLST)))      )
      (command "_.LAYER" "_OFF" "*" "_Y")
      (foreach VAL LAYLST (command "_ON" VAL))
      (command "")            (if (= (length LAYLST) 1)
        (prompt (strcat "\nLayer " (car LAYLST) " da tach ra."))
        (prompt (strcat "\n" (itoa (length LAYLST)) " layers da tach ra. "
                        "Layer " LAY " la hien hanh."   )  )  )  )  )  (princ) )
(defun c:Ll () (layiso)) 
(Defun C:LO () (setvar "cmdecho" 0)  (Command "_.LAYER" "_ON" "*" "") (princ "\nDa hien toan bo cac Layer !") (princ))
(defun c:bg () (command "_.blipmode" "_off"))
;VE NET CAT
(defun C:CA ()
(SETQ OLDERR *error*
      *error* myerror)
(SETQ CMD (GETVAR "CMDECHO"))
(SETQ OSM (GETVAR "OSMODE"))
(SETVAR "CMDECHO" 0)
(SETQ DK1 (GETVAR "USERR3"))
(IF (= DK1 0)
    (PROGN
     (SETQ STR "1")
     (SETVAR "USERR3" 1)
    )	
    (SETQ STR (RTOS DK1))
)
(SETQ PRPT (STRCAT "\nSize: <" STR ">:"))
(SETQ DK1 (GETREAL PRPT))
(IF (= DK1 NIL)
    (SETQ DK1 (GETVAR "USERR3"))
    (SETVAR "USERR3" DK1)
)
(setq v (getvar "osmode"))
(setq pt1 (getpoint "\nDiem dau : "))
(setq pt2 (getpoint "\nDiem cuoi : " pt1))
(command "osnap" "none")
(setq dk (* dk1 100))
(setq goc (angle pt1 pt2))
(setq kcach (distance pt1 pt2))
(setq pt3 (polar pt1 goc (- (/ kcach 2) (* 0.75 DK))))
(setq pt4 (polar pt1 goc (+ (/ kcach 2) (* 0.75 DK))))
(setq pt5 (polar pt3 (+ (/ PI 2) goc)   DK))
(setq pt6 (polar pt4 (- goc (/ PI 2))    DK))
(setq pt7 (polar pt1 (+ goc pi) (* 2 (/ DK 5))))
(setq pt8 (polar pt2  goc  (* 2 (/ DK 5))))
(command "layer" "m" "manh" "c" "163" """")
(command "pline"  pt7 pt1 pt3 pt5 pt6 pt4 pt2 pt8 "")
(setvar "osmode" v ))
;VE CAO TRINH
(DEFUN C:CT (/ CMD PT1 PT2 PT3 PT4 PT5 PT6 PT7 PT8 NPI TX DX DY TL OSM OLL
		CRST RSIZE TSIZE STR PRMT FCH NBC OLDERR)
(SETQ OLDERR *error*
      *error* loisb)
(command "layer" "m" "ghichu" "c" "150" """")
(SETQ CMD (GETVAR "CMDECHO"))
(SETQ NBC (GETVAR "CLAYER"))
(SETQ OSM (GETVAR "OSMODE"))
(SETVAR "CMDECHO" 0)
(SETQ PT1 (GETPOINT "\nDiem cao trinh:"))
(SETQ TX "%%p0.00");;(GETSTRING "\nCao trinh:"))
(SETQ FCH (SUBSTR TX 1 1))
(IF (= FCH "@") (SETQ TX (STRCAT "%%P" (SUBSTR TX 2 (- (STRLEN TX) 1)))))
(SETQ CRST (GETVAR "TEXTSTYLE"))
(SETQ RSIZE (CDR (ASSOC 40 (TBLSEARCH "STYLE" CRST))))
(SETQ TSIZE (GETVAR "TEXTSIZE"))
(SETQ STR (RTOS TSIZE 2))
(SETQ PRMT (STRCAT "\nText height <" STR ">:"))
(IF (= RSIZE 0)
  (PROGN
	(INITGET 4)
	(SETQ TSIZE (GETREAL PRMT))
	(IF (= TSIZE NIL) (SETQ TSIZE (GETVAR "TEXTSIZE"))
			  (SETVAR "TEXTSIZE" TSIZE))
  )
)
(PRINC)
(SETQ TL (/ (GETVAR "TEXTSIZE") 2))
(SETVAR "OSMODE" 0)
(SETQ DX (CAAR (CDR (TEXTBOX (LIST (CONS 1 TX))))))
(SETQ NPI (/ PI 2))
(SETQ PT4 (POLAR PT1 NPI (* 1 TL)))
(SETQ PT2 (POLAR PT4 PI (* 2 TL)))
(SETQ PT3 (POLAR PT4 0 (* 2 TL)))
(SETQ PT5 (POLAR PT4 NPI (* 5 TL)))
(SETQ PT6 (POLAR PT2 NPI  TL))
(SETQ PT7 (POLAR PT6 0 (+ (* 3.7 TL) DX)))
(SETQ PT8 (POLAR PT6 NPI (* 1 TL)))
(SETQ PT8 (POLAR PT8 0 (* 2.5 TL)))
(SETQ PT9 (POLAR PT1 pi (* 2 TL)))
(SETQ PT10 (POLAR PT1 0 (* 2 TL)))
(COMMAND "COLOR" "84" "")
(COMMAND "STYLE" "BEO"  ".VnArialH" "" "" "" "" "")
(IF (= RSIZE 0)(COMMAND "TEXT" PT8 TSIZE 0 tX) (COMMAND "TEXT" PT8 0 TX))
(COMMAND "COLOR" "7" "")
(COMMAND "SOLID" PT1 PT2 PT4 "" "" "pLINE"  PT1 pt3 pt2  "")
(COMMAND "COLOR" "150" "")
(COMMAND "pLINE" PT1 PT5 "" "pLINE" PT6 PT7 "" "pLINE" pt9 pt10"")
(SETVAR "CLAYER" "0")
(command "ddedit" pause)
(COMMAND "COLOR" "BYLAYER" "")
(SETVAR "CMDECHO" CMD)
(SETVAR "CLAYER" NBC)
(SETVAR "OSMODE" OSM)
(PRINC)
)

;VE THEP AM
(DEFUN C:SA (/ OLDERR CMD OSM DK PT1 PT2  STR PRPT GOCX 
				PTD PTC)
(SETQ OLDERR *error*
      *error* myerror)
(command "layer" "m" "thep" "c" "6" """")
(SETQ CMD (GETVAR "CMDECHO"))
(SETQ OSM (GETVAR "OSMODE"))
(SETVAR "CMDECHO" 0)
(SETQ DK (GETVAR "USERR3"))
(IF (= DK 0)
    (PROGN
     (SETQ STR "1")
     (SETVAR "USERR3" 1)
    )	
    (SETQ STR (RTOS DK))
)
(SETQ PRPT (STRCAT "do dai moc: <" STR ">:"))
(SETQ DK (GETREAL PRPT))
(IF (= DK NIL)
    (SETQ DK (GETVAR "USERR3"))
    (SETVAR "USERR3" DK)
)
(INITGET 7)
(SETQ PTD (GETPOINT "\nFrom point:"))
(INITGET 7)
(SETQ PTC (GETPOINT PTD "\nTo point:"))
(SETVAR "OSMODE" 0)
(SETQ GOCX (ANGLE PTD PTC))

(SETQ PT1 (POLAR  PTD  (- GOCX  (/ pi 2))   (* 150 DK)))
(SETQ PT2 (POLAR  PTC  (- GOCX  (/ pi 2))   (* 150 DK)))
(COMMAND "PLINE"   pt1 ptd ptc pt2   "")
(SETVAR "OSMODE" OSM)
(SETVAR "CMDECHO" CMD)
(PRINC)
)
;VE THEP DUOI
(DEFUN C:SD (/ OLDERR CMD OSM DK PT1 PT2 PT3 PT4 PT5 PT6 STR PRPT GOCX GOCY
				PTD PTC)
(SETQ OLDERR *error*
      *error* myerror)
(command "layer" "m" "thep" "c" "6" """")
(SETQ CMD (GETVAR "CMDECHO"))
(SETQ OSM (GETVAR "OSMODE"))
(SETVAR "CMDECHO" 0)
(SETQ DK (GETVAR "USERR3"))
(IF (= DK 0)
    (PROGN
     (SETQ STR "1")
     (SETVAR "USERR3" 100)
    )	
    (SETQ STR (RTOS DK))
)
(SETQ PRPT (STRCAT "Duong kinh moc tron <" STR ">:"))
(SETQ DK (GETREAL PRPT))
(IF (= DK NIL)
    (SETQ DK (GETVAR "USERR3"))
    (SETVAR "USERR3" DK)
)
(INITGET 7)
(SETQ PTD (GETPOINT "\nFrom point:"))
(INITGET 7)
(SETQ PTC (GETPOINT PTD "\nTo point:"))
(SETVAR "OSMODE" 0)
(SETQ GOCX (ANGLE PTD PTC))
(SETQ GOCY (+ GOCX (/ PI 2)))
(SETQ PT1 (POLAR PTD GOCX (/ (* 100 DK) 2)))
(SETQ PT2 (POLAR PTC (+ GOCX PI) (/ (* 100 DK) 2)))
(SETQ PT3 (POLAR PT1 GOCY (* 100 DK)))
(SETQ PT4 (POLAR PT2 GOCY (* 100 DK)))
(SETQ PT5 (POLAR PT3 GOCX (* 100 DK)))
(SETQ PT6 (POLAR PT4 (+ GOCX PI) (* 100 DK)))
(COMMAND "PLINE" PT5 PT3 "A" PT1 "L" PT2 "A" PT4 "L" PT6 "")
(SETVAR "OSMODE" OSM)
(SETVAR "CMDECHO" CMD)
(PRINC)
)
;GHI CHU THEP
(DEFUN C:tH ()
(SETQ DK1 (GETVAR "USERR3"))
(IF (= DK1 0)
    (PROGN
     (SETQ STR "1")
     (SETVAR "USERR3" 1)
    )	
    (SETQ STR (RTOS DK1))
)
(SETQ PRPT (STRCAT "\nSize <" STR ">:"))
(SETQ DK1 (GETREAL PRPT))
(IF (= DK1 NIL)
    (SETQ DK1 (GETVAR "USERR3"))
    (SETVAR "USERR3" DK1)
)
(setq dk (* dk1 50))
(INITGET 7)
 (SETQ PTD (GETPOINT "\nFrom point:"))
(INITGET 7)
(SETQ PTC (GETPOINT PTD "\nTo point:"))
(SETQ GOCX (ANGLE PTD PTC))
(SETQ GOCY (+ GOCX (/ PI 2)))
(setq v (rtos dk))
(setq t (distance ptd ptc))
(setq r (/ t 2))
(SETQ PT1 (POLAR  PTc  0   (* 14 DK)))
(SETQ o (POLAR  PT1  0   (* 2.5 DK)))
(setq h (substr v 1 1))
(setq y (substr v 2 3))
(setq l (distance ptc pt1))
(setq pt3 (polar ptc 0 (/ l 2)))
(setq pt4 (polar pt3 (/ pi 2) (* 2 DK)))
(setq pt5 (polar ptd (- gocx (/ pi 2)) r))
(setq pt6 (polar ptd (+ gocx (/ pi 2)) r))
(setq pt7 (polar ptd (+ gocx  pi) r))
(setq pt8 (polar ptd  gocx   (* 2.8 dk)))
(command "osnap"  "")
(command "layer" "m" "ghichu" "c" "150" """")
(COMMAND "COLOR" "84" "")
(COMMAND "STYLE" "thep"  "romans.shx,vn1.shx" "" "" "" "" "" "" )
(command "text" "j" "m" pt4 (* 2.5 DK) 0)
(command "%%c8a150" )
(COMMAND "STYLE" "BEO"  ".VnArialH" "" "" "" "" "")
(command "text" "j" "m" o (* 2.7 DK) 0)
(command "1" "")
(COMMAND "COLOR" "4" "")
(command "circle" o (* 2.5 DK)"")
(COMMAND "COLOR" "150" "")
(COMMAND "PLINE" ptd "w" "" (* 0.5 dk) pt8  "w" "" 0 pt8 ptc pt1  "")
(COMMAND "COLOR" "BYLAYER" "")
(command "osnap" "End,Mid,Cen,Quad,Int,Perp,Tan,Near,App,Int,Ext,Par"  )
(command "ddedit" pause)
)
;ghi chu thep san
(DEFUN C:ts ()
(SETQ DK1 (GETVAR "USERR3"))
(IF (= DK1 0)
    (PROGN
     (SETQ STR "1")
     (SETVAR "USERR3" 1)
    )	
    (SETQ STR (RTOS DK1))
)
(SETQ PRPT (STRCAT "\nSize <" STR ">:"))
(SETQ DK1 (GETREAL PRPT))
(IF (= DK1 NIL)
    (SETQ DK1 (GETVAR "USERR3"))
    (SETVAR "USERR3" DK1)
)
(setq dk (* dk1 50))
(INITGET 7)
 (SETQ PTD (GETPOINT "\nFrom point:"))
(INITGET 7)
(SETQ PTC (GETPOINT PTD "\nTo point:"))
(SETQ GOCX (ANGLE PTD PTC))
(SETQ GOCY (+ GOCX (/ PI 2)))
(setq v (rtos dk))
(setq t (distance ptd ptc))
(setq r (/ t 2))
(SETQ PT1 (POLAR  PTc  0   (* 14 DK)))
(SETQ o (POLAR  PT1  0   (* 7 DK)))
(SETQ o3 (POLAR  o  pi   (* 2.5 DK)))
(SETQ o1 (POLAR  o  (/ pi 2) (* 2.5 DK)))
(SETQ o2 (POLAR  o  (- 0 (/ pi 2)) (* 2.5 DK)))
(setq h (substr v 1 1))
(setq y (substr v 2 3))
(setq l (distance ptc o3))
(setq pt3 (polar ptc 0 (/ l 2)))
(setq pt4 (polar pt3 (/ pi 2) (* 2 DK)))
(setq pt14 (polar pt3 (- 0 (/ pi 2)) (* 2 DK)))
(setq pt5 (polar ptd (- gocx (/ pi 2)) r))
(setq pt6 (polar ptd (+ gocx (/ pi 2)) r))
(setq pt7 (polar ptd (+ gocx  pi) r))
(setq pt8 (polar ptd  gocx   (* 2.8 dk)))
(command "osnap"  "")
(command "layer" "m" "ghichu" "c" "150" """")
(COMMAND "COLOR" "84" "")
(COMMAND "STYLE" "thep"  "romans.shx,vn1.shx" "" "" "" "" "" "")
(command "text" "j" "m" pt4 (* 2.5 DK) 0)
(command "/g10a150" )
(command "text" "j" "m" pt14 (* 2.5 DK) 0)
(command "%%c6a200" )
(COMMAND "STYLE" "BEO"  ".VnArialH" "" "" "" "" "")
(command "text" "j" "m" o1 (* 2.7 DK) 0)
(command "1" "")
(command "text" "j" "m" o2 (* 2.7 DK) 0)
(command "2" "")
(COMMAND "COLOR" "4" "")
(command "circle" o1 (* 2.5 DK)"")
(command "circle" o2 (* 2.5 DK)"")
(COMMAND "COLOR" "150" "")
(COMMAND "PLINE" ptd "w" "" (* 0.5 dk) pt8  "w" "" 0 pt8 ptc  o "")
(COMMAND "COLOR" "BYLAYER" "")
(command "osnap" "End,Mid,Cen,Quad,Int,Perp,Tan,Near,App,Int,Ext,Par"  )
(command "ddedit" pause)
)
;VE CUA
(defun C:C1 (/ p1 p2 p3 p4 side dis wid ang angsile old)
 (setq old (getvar "OSMODE")) 
 (setvar "OSMODE" 171)
(command "osnap"  "")
(command "osnap" "End,Mid,Cen,Quad,Int,Perp,Tan,Near,App,Int,Ext,Par"  )
 (setq p1 (getpoint "\nStart point:"))
 (setq p2 (getpoint p1 "\nEnd point:"))
 (setq side (getpoint p2 "\nOpen side"))
 (setq dis (distance p1 p2))
 (setq ang (angle p1 p2))
 (if (< ang (angle p1 side))
  (setq angside    (/ pi 2) )
  (setq angside (- (/ pi 2))) )
 (if  (>= (- (angle p1 side) ang) pi)
  (setq angside (- (/ pi 2))) )
 (if  (>= (- ANG (angle p1 side) ) pi)
  (setq angside (/ pi 2)) )
 (setq p3 (polar p2 (+ ang angside) dis) )
 (setq p4 (polar p1 (+ ang angside) dis) )
 (setq wid (/ dis 15))
 (setvar "OSMODE" 0)
(command "layer" "m" "cua" "c" "44" """")
 (command "PLINE" p1 "A" "D" p4 "0.5" p3 "L" p2 
                  (polar p2 (+ ang pi) wid) 
                  (polar p3 (+ ang pi) wid)  "")
(setvar "OSMODE" old)
(command "osnap"  "")
(command "osnap" "End,Mid,Cen,Quad,Int,Perp,Tan,Near,App,Int,Ext,Par"  )
 (princ))
(defun C:C2 (/ p1 p2 p3 p4 side dis wid ang angsile old)
 (defun cua1 (pt1 pt2)
  (setq p1 pt1
        p2 pt2)
  (setq ang (angle p1 p2))
  (if (< ang (angle p1 side))
   (setq angside    (/ pi 2) )
   (setq angside (- (/ pi 2)))  )
  (if  (>= (- (angle p1 side) ang) pi)
   (setq angside (- (/ pi 2)))  )
  (if  (>= (- ANG (angle p1 side) ) pi)
   (setq angside (/ pi 2))  )
  (setq p3 (polar p2 (+ ang angside) dis) )
  (setq p4 (polar p1 (+ ang angside) dis) )
  (setq wid (/ dis 15)) 
(command "layer" "m" "cua" "c" "44" """")
  (command "PLINE" p1 "A" "D" p4 p3 "L" p2 
                   (polar p2 (+ ang pi) wid) 
                   (polar p3 (+ ang pi) wid) 
  "")
 )
 ;; ------------------------------------
 (setq old (getvar "OSMODE")) 
 (setvar "OSMODE" 171)
(command "osnap"  "")
(command "osnap" "End,Mid,Cen,Quad,Int,Perp,Tan,Near,App,Int,Ext,Par"  )
 (setq p1 (getpoint "\nStart point:"))
 (setq p2 (getpoint p1 "\nEnd point:"))
 (setq side (getpoint p2 "\nOpen side"))
 (setq dis (distance p1 p2))
 (setq dis (/ dis 2))
 (setvar "OSMODE" 0)
 (setq p1 (polar p1 (angle p1 p2) dis))
 (cua1 p1 p2)  
 (setq ang (+ ang pi))
 (setq p2 (polar p1 ang dis))
 (cua1 p1 p2)  
 (setvar "OSMODE" old)
(command "osnap"  "")
(command "osnap" "End,Mid,Cen,Quad,Int,Perp,Tan,Near,App,Int,Ext,Par" )
 (princ)
)
; Duong han
(defun C:HJ ( / p1 p2 p3 p4 a b l n deltaX deltaY i x1 y1 x2 y2 )
(command "layer" "m" "manh" "c" "163" """")
       (setq p1 (getpoint "Start point : ") )
       (setq p2 (getpoint p1 "End point   : ") )
      (setq a  (getdist  "Distance    : ") )
      (setq b  (getdist  "Lenght      : ") )
       (setq l  (distance p1 p2) )
       (setq n  (fix ( / l a ) ) )
       (setq deltaX ( - (car p2) (car p1) ) )
       (setq deltaY ( - (cadr p2) (cadr p1) ) )
       (setq i 0)
       (setvar "OSMODE" 0)
       (while (<= i n)
        (setq x1 ( + (car p1) (* i (* (/ a l) deltaX ) ) ))
        (setq y1 ( + (cadr p1) (* i (* ( / a l ) deltaY ) ) ) )
        (setq p3 (list x1 y1) )
        (setq x2 ( + x1 (* -1 (* b (/ deltaY l) )) ) ) 
        (setq y2 ( + y1 (* b (/ deltaX l)))) 
        (setq p4 (list x2 y2) )
        (command "LINE" p3 p4 "")
        (setq i (+ i 1) ))
       (setvar "OSMODE" 171))
;ky hieu cat
(defun C:bc ()
(setq bk (getvar "USERR3"))
(if (= bk 0)
  (progn
    (setq cont "1")
    (setvar "USERR3" 1)
    )
	(setq cont (rtos bk))
)

(setq pt1 (getpoint "\n Nhap diem dat:"))
(command "layer" "m" "ghichu" "c" "150" """")
(command "osnap"  "")
(COMMAND "COLOR" "4" "")
(command "circle" pt1 110"")
(setq gc (getorient "\n Ban nhap goc:"))
(if (= gc nil)
	(progn
	(setq goc 0)
	)
	(setq goc gc)
	)
(setq pt2 (polar pt1  goc 110))
(setq pt3 (polar pt1 (+ goc (/ pi 1)) 110))
(setq pt4 (polar pt1  goc 220))
(setq pt5 (polar pt1 (+ goc (/ pi 1)) 220))
(setq pt6 (polar pt1 (- goc (/ pi 2)) 110))
(setq pt7 (polar pt1 (- goc (/ pi 2)) 220))
(setq pt8 (polar pt1 (+ goc (/ pi 2)) 110))
(setq pt10 (polar pt1  0 110))
(setq pt9 (polar pt1 (- goc (/ pi 4)) (* 1 150)))
(COMMAND "COLOR" "150" "")
(command "pline" pt2 pt4 pt7 pt6 "a" "r" pt6 pt1 pt2"")
(command "pline" pt7 pt5 pt3"")
(setq dk (strcat "\n Size:<"cont">"))
(setq bk (getreal dk))
(if (= bk nil)
 (progn
  (setq bk (getvar "USERR3"))
	)
  (setvar "USERR3" bk)
  
)
(command "scale" pt6 pt5 pt8 pt4"" pt1 bk"")
(COMMAND "STYLE" "BEO"  ".VnArialH" "" "" "" "" "")
(COMMAND "COLOR" "84" "")
(command "text" "j" "mc" pt1 (* 110 bk) pt10 "A" "") 
(setq p4 (polar pt1  goc (* bk 200)))
(COMMAND "COLOR" "7" "")
(command "hatch"  "solid" p4 "")
(command "osnap" "End,Mid,Cen,Quad,Int,Perp,Tan,Near,App,Int,Ext,Par"  )
(COMMAND "COLOR" "BYLAYER" "")
(command "ddedit")
)
;Ve cua
(defun c:wd ()
 (setvar "osmode" 512 )
(command "osnap"  "")
(command "osnap" "End,Mid,Cen,Quad,Int,Perp,Tan,Near,App,Int,Ext,Par"  ) 
 (setq p1 (getpoint "\nfirst point :"))
 (if (= nil p1)(sdor)(odor))
)
(defun odor ()
 (setq p2 (getpoint p1 "\nsecond point width open :"))
 (setvar "osmode" 128 ) 
 (setq p3 (getpoint p2 "\npick in wall :")
       p31 (polar p1 (angle p2 p3) (distance p2 p3))
 )
 (setvar "osmode" 0 )
(command "layer" "m" "TUONG" "c" "31" """") 
(command "osnap"  "")
 (command  "line" p1 p31 "")
 (setq s1 (entlast));de copy ve do cua so
 (command  "line" p2 p3 "" "trim" "c" p3 p1 "" 
                   (polar p1 (angle p1 p2) (/ (distance p1 p2) 2))
                   (polar p31 (angle p1 p2) (/ (distance p1 p2) 2)) ""
 )
 (setq sel (strcase (getstring "\nWin Open <Dor> :")))
 (cond ((= sel "W")(openwin))
       ((= sel "")(opendor))
       (T (princ))
 )
 (princ)                            
)
(defun sdor ()
 (setvar "osmode" 1 ) 
 (setq p1 (getpoint "\nfirst point :"))
 (setq p2 (getpoint p1 "\nsecond point width open :"))
 (setvar "osmode" 128 ) 
 (setq p3 (getpoint p2 "\npick in wall :")
       p31 (polar p1 (angle p2 p3) (distance p2 p3))
 )
 (setvar "osmode" 0 ) 
(command "osnap"  "")
(command "layer" "m" "cua" "c" "115" """")
 (command  "line" p1 p31 "")
 (setq s1 (entlast)) ;de copy ve do cua so
 (setq sel (strcase (getstring "\nWin Open <Dor> :")))
 (cond ((= sel "W")(openwin))
       ((= sel "")(opendor))
       (T (princ))
 )
 (princ)                            
)
;-----------
(defun opendor ()
(setq pt (polar (polar p1 (angle p1 p2) (/ (distance p1 p2) 2)) (angle p3 p2) 13))
 (setq ang (angle (polar p1 (angle p1 p2) (/ (distance p1 p2) 2)) pt)
       nsegdor (getint "\nnumber seg dor 2 4 <1> :")
 )
 (cond ((= nsegdor 2)(dor2 p1 p2 ang))
       ((= nsegdor 4)(dor4 p1 p2 ang))
       (T (dor p1 p2 ang))
 )
)
;----------
(defun dor4 (p1 p2 ang)
 (setq p12 (polar p1 (angle p1 p2) (/ (distance p1 p2) 2)))
 (setq p112 (polar p1 (angle p1 p12) (/ (distance p1 p12) 2)))
 (setq p122 (polar p12 (angle p1 p12) (/ (distance p1 p12) 2)))
 (dor p1 p112 ang)(dor p112 p12 ang)(dor p2 p122 ang)(dor p122 p12 ang)
)
;----------
(defun dor2 (p1 p2 ang)
 (setq p12 (polar p1 (angle p1 p2) (/ (distance p1 p2) 2)))
 (dor p1 p12 ang)(dor p2 p12 ang)
)
;----------
(defun dor (p1 p2 ang)
 (setq ps1 (polar p1 (angle p1 p2) 30)
       ps2 (polar ps1 ang (distance p1 p2))
       ps3 (polar ps2 (angle p2 p1) 30)
 )
(command "osnap"  "")
(command "layer" "m" "cua" "c" "44" """")
 (command "pline" ps3 ps2 ps1 p1 ps3 ps2 "a" p2 "" ) 
)
;----------
(defun openwin ()
(command "osnap"  "")
(command "layer" "m" "cua" "c" "44" """")
 (command "line" p1 p2 "" "line" p31 p3 ""
          "line" (polar p1 (angle p2 p3) (/ (distance p2 p3) 2))
                 (polar p2 (angle p2 p3) (/ (distance p2 p3) 2)) ""
 )
 (setq nsegwin (getint "\nnumber seg win :")
        disseg (/ (distance p1 p2) nsegwin)   
 )
 (setq lispoiseg nil)
 (repeat (- nsegwin 1)
  (setq lispoiseg (append lispoiseg (list (polar p1 (angle p1 p2) (* (- nsegwin 1) disseg))))
          nsegwin (- nsegwin 1)
  )
 )
 (command "copy" s1 "" "m" p1)
 (foreach p lispoiseg (command p))  
(command "osnap"  "")
(command "osnap" "End,Mid,Cen,Quad,Int,Perp,Tan,Near,App,Int,Ext,Par"  )
(command "")
)
(PRINC) 
;-----------
;ki hieu truc
(defun C:vc ()
(setq bk (getvar "USERR3"))
(if (= bk 0)
  (progn
    (setq cont "1")
    (setvar "USERR3" 1)
    )
	(setq cont (rtos bk))
)
(setq pt1 (getpoint "\n Nhap diem dat:"))
(command "layer" "m" "ghichu" "c" "150" """")
(command "osnap"  "")
(COMMAND "COLOR" "4" "")
(command "circle" pt1 150 "")
(setq pt2 (polar pt1 0 150))
(setq pt3 (polar pt1 (/ pi 1) 150))
(setq pt4 (polar pt1 0 300))
(setq pt5 (polar pt1 (/ pi 1) 300))
(setq pt6 (polar pt1 (- 0 (/ pi 2)) 150))
(setq pt7 (polar pt1 (- 0 (/ pi 2)) 300))
(setq pt8 (polar pt1 (/ pi 2) 150))
(setq pt9 (polar pt1 (/ pi 2) 300))
(setq pt10 (polar pt1 0 150))
(setq pt11 (polar pt1 (/ pi 4) 150))
(COMMAND "COLOR" "150" "")
(command "line" pt2 pt4 "")
(command "line" pt6 pt7 "")
(command "line" pt3 pt5 "")
(command "line" pt8 pt9 "")
(setq dk (strcat "\n Size:<"cont">"))
(setq bk (getreal dk))
(if (= bk nil)
 (progn
  (setq bk (getvar "USERR3"))
	)
  (setvar "USERR3" bk)
  )
(command "scale" pt4 pt5 pt7 pt9 pt11"" pt1 bk"")
(COMMAND "COLOR" "84" "")
(COMMAND "STYLE" "BEO"  ".VnArialH" "" "" "" "" "")
(command "text" "j" "mc" pt1 (* 150 bk) pt10 "A" "") 
(COMMAND "COLOR" "BYLAYER" "")
(command "osnap" "End,Mid,Cen,Quad,Int,Perp,Tan,Near,App,Int,Ext,Par" )
(command "move")
)
(princ)
(defun c:qq ()
             (command ".zoom" "e")
             (command ".qsave") 
             (command ".close") 
)
(defun c:bn()
(command "osnap"  "")
(command "osnap" "End,Mid,Cen,Quad,Int,Perp,Tan,Near,App,Int,Ext,Par"  )
)
