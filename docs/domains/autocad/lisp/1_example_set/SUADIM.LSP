;***************************************************************************
;* NAME     :   Ch­¬ng tr×nh söa KÝch th­íc                          
;* WRITTEN  :        §ç Hoµng Hoµnh - §¹i häc KiÕn Tróc HN        
;***************************************************************************


;*************Söa ®é dµi d­êng giãng trªn cña kÝch th­íc ®o trôc X********************************
(DEFUN YD ()
 (SETQ CMD (GETVAR "CMDECHO"))
 (SETVAR "CMDECHO" 0)
 (COMMAND "UCS" "W")
 (SETVAR "CMDECHO" 1)
 (PROMPT"\nChän kÝch th­íc ®o trôc X muèn canh lÒ")
 (SETQ SET (SSGET))
 (PROMPT"\nChän vÞ trÝ phÇn më réng míi ")
 (SETQ P1 (GETPOINT))
 (SETQ Y3 (CADR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L13 (ASSOC 13 A))
     (SETQ M13 (CDR L13))
     (SETQ L14 (ASSOC 14 A))
     (SETQ M14 (CDR L14))
     (SETQ P13 (LIST 13 (CAR M13) Y3 (CADDR M13)))
     (SETQ T13 (CDR P13))
     (SETQ P14 (LIST 14 (CAR M14) Y3 (CADDR M14)))
     (SETQ A (SUBST P13 L13 A))
     (SETQ A (SUBST P14 L14 A))
     (ENTMOD A)			
    )
   )
  (SETQ INDEX (+ INDEX 1))
 )
 (SETVAR "CMDECHO" 0)
 (COMMAND "UCS" "P")
 (SETVAR "CMDECHO" CMD)
)
(DEFUN C:XX () (YD) )

;*********************Söa ®é dµi ®­êng giãng trªn cña kÝch th­íc  ®o trôc Y**********************
(DEFUN XD ()
 (SETQ CMD (GETVAR "CMDECHO"))
 (SETVAR "CMDECHO" 0)
 (COMMAND "UCS" "W")
 (SETVAR "CMDECHO" 1)
 (PROMPT"\nChän kÝch th­íc ®o trôc Y muèn canh lÒ")
 (SETQ SET (SSGET))
 (PROMPT"\nChän vÞ trÝ ®­êng giãng míi")
 (SETQ P1 (GETPOINT))
 (SETQ X3 (CAR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L13 (ASSOC 13 A))
     (SETQ M13 (CDR L13))
     (SETQ L14 (ASSOC 14 A))
     (SETQ M14 (CDR L14))
     (SETQ P13 (LIST 13 X3 (CADR M13) (CADDR M13)))
     (SETQ P14 (LIST 14 X3 (CADR M14) (CADDR M14)))
     (SETQ A (SUBST P13 L13 A))
     (SETQ A (SUBST P14 L14 A))
     (ENTMOD A)			
    )
   )
  (SETQ INDEX (+ INDEX 1))
 )
 (SETVAR "CMDECHO" 0)
 (COMMAND "UCS" "P")
 (SETVAR "CMDECHO" CMD)
 (PRINC)
)
(DEFUN C:YY () (XD) )


;*************Söa ®é dµi d­êng giãng d­íi cña kÝch th­íc ®o trôc Y********************************
(DEFUN X-ALDIM ()
 (SETQ CMD (GETVAR "CMDECHO"))
 (SETVAR "CMDECHO" 0)
 (COMMAND "UCS" "W")
 (SETVAR "CMDECHO" 1)
 (PROMPT"\nChän kÝch th­íc ®o trôc Y muèn canh lÒ")
 (SETQ SET (SSGET))
 (PROMPT"\nChän vÞ trÝ kÝch th­íc míi")
 (SETQ P1 (GETPOINT))
 (SETQ X3 (CAR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L10 (ASSOC 10 A))
     (SETQ M10 (CDR L10))
     (SETQ L11 (ASSOC 11 A))
     (SETQ M11 (CDR L11))
     (SETQ P10 (LIST 10 X3 (CADR M10) (CADDR M10)))
     (SETQ A (SUBST P10 L10 A))
     (ENTMOD A)			
    )
   )
  (SETQ INDEX (+ INDEX 1))
 )
 (SETVAR "CMDECHO" 0)
 (COMMAND "UCS" "P")
 (SETVAR "CMDECHO" CMD)
)
(DEFUN C:X-ALDIM () (X-ALDIM) )
(DEFUN C:AY () (X-ALDIM) )

;*************Söa ®é dµi d­êng giãng d­íi cña kÝch th­íc ®o trôc X********************************
(DEFUN Y-ALDIM ()
 (SETQ CMD (GETVAR "CMDECHO"))
 (SETVAR "CMDECHO" 0)
 (COMMAND "UCS" "W")
 (SETVAR "CMDECHO" 1)
 (PROMPT"\nChon vi tri kich thuoc muon canh le")
 (SETQ SET (SSGET))
 (PROMPT"\nChon vi tri kich thuoc moi")
 (SETQ P1 (GETPOINT))
 (SETQ Y3 (CADR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L10 (ASSOC 10 A))
     (SETQ M10 (CDR L10))
     (SETQ P10 (LIST 10 (CAR M10) Y3 (CADDR M10)))
     (SETQ A (SUBST P10 L10 A))
     (ENTMOD A)			
    )
   )
  (SETQ INDEX (+ INDEX 1))
 )
 (SETVAR "CMDECHO" 0)
 (COMMAND "UCS" "P")
 (SETVAR "CMDECHO" CMD)
)
(DEFUN C:Y-ALDIM () (Y-ALDIM) )
(DEFUN C:AX      () (Y-ALDIM) )
