;this program can draw the famous spiral curve(klothiod)(الكلوتوئيد)
;which is widley used in road  horizontal curves designing
;I discuse here two kind of klothoid first with two branch second with single branch when
;it start tangent a line to tangent a circle
;in the first situation you will prompt to define the two tangent line(three point)
;then you will be asked for designed length of klothoid you can enter any value
;then the program will give you the minimum radias which make the two branch of klothiod
;touch each other without creating curve then you must enter designed radias concerning minimum radias
;then you will prompt for interval between points which will form the spiral
;you will get the spiral with all calculation written at the top of spiral
;second situation you will prompt to choose three point of the circle to define it
;then two points to define the line after that direction of spiral right or left
;then interval between points (please check the attached drawing to see parametre)
;to use the program load it then enter at the command line: kloto
;for any inquiry please don't hesitate e.mail [email removed] or tel:0096341437033(syria)

(defun c:kloto ()
 
(setq oom (getvar "osmode"))
  (setq andr(getvar"angdir"))
 (setvar "angdir"1)
 (setq andb(getvar"angbase")) 
(setvar "angbase"(/ pi 2))
(setq aunt(getvar"aunits"))  
(setvar "aunits"2)
  (setvar "dimaunit"2)
  (setvar"dimadec"4)


  (initget "1 2")
 (setq br (getkword "\n is kloto 1-branch or 2-branch:"))
    (if(= br "2")
	(progn
(setq p1 (getpoint "\n enter a point on first line")
      pc (getpoint "\n enter intersection point")
      p2 (getpoint "\n enter any point on second line")
      )
(setq ang1 (angle pc p1)
      ang2 (angle pc p2)
      ang (- ang1 ang2)
      ang0 (abs ang)
      )
(if(<= ang0 pi)
  (setq ar (- pi ang0))
  (setq ar (- ang0 pi))
  )
(setq a (/ (* 200 ar)pi))
(setq l0 (getreal "\n enter length of klotoeed:"))
(setq Rmin (/(* 200 l0)(* a pi)))
(princ "minmum radias=")
(princ (rtos Rmin 2 3))
(setq r0 (getreal (strcat"\n enter design radias(R>="(rtos rmin 2 3)" ): ")))
(setq u (/ l0(* 2 r0)))
(setq t0 (/(* 200 u)pi))
(princ "T0=")
(princ t0)
(setq i (sqrt(* 2(* l0 r0))))
(setq u1 (expt u 0.5)
      u2 (/(expt u 2.5)10)
      u3 (/(expt u 4.5)216)
      u4 (/(expt u 6.5)9360)
      u5 (/(expt u 8.5)685440)
      u6 (/(expt u 10.5)76204800)
      u7 (/(expt u 1.5)3)
      u8 (/(expt u 3.5)42)
      u9 (/(expt u 5.5)1320)
      u10 (/(expt u 7.5)80640)
      u11 (/(expt u 9.5)6894720)
      )
(setq x0 (* i (-(+(-(+(- u1 u2)u3)u4)u5)u6)))
(setq y0 (* i (+(-(+(- u7 u8)u9)u10)u11)))
(setq m1 (sin(-(/ ar 2)u)))
(setq m2 (cos(-(/ ar 2)u)))
(setq m0 (/ m1 m2))
(setq m (*(* r0 m0)(cos u)))
(setq m3 (sin(/ ar 2)))
(setq m4 (cos(/ ar 2)))
(setq b1 (/ m3 m4))
(setq b (* y0 b1))
(setq c (*(*(* r0 (sin u))b1)m0))
(setq s (+(+(+ x0 m)b)c))
(setq st1 (polar pc ang1 s))
(setq st2 (polar pc ang2 s))
(setvar "osmode" 0)
(command "point" (list (car st1) (cadr st1)))
(command "point" (list (car st2) (cadr st2)))
(setq st3 (polar st1 (+ ang1 (/ pi 2)) 100))
(setq st4 (polar st2 (+ ang2 (* 0.5 pi))100))
(setq ps (inters st1 st3 st2 st4 nil))
(command "ucs" "New" "3p" st1 pc ps )
(command "point" (list x0 y0))
(setq sn (getreal "\n enter interval between points:"))
(setq k 1)
(setq n (/ l0 sn))
(while (<= k n)
  (progn
    (setq ln (* k sn))
    (setq v (/(expt ln 2)(expt i 2)))
    (setq v1 (expt v 0.5)
          v2 (/(expt v 2.5)10)
          v3 (/(expt v 4.5)216)
          v4 (/(expt v 6.5)9360)
          v5 (/(expt v 8.5)685440)
          v6 (/(expt v 10.5)76204800)
          v7 (/(expt v 1.5)3)
          v8 (/(expt v 3.5)42)
          v9 (/(expt v 5.5)1320)
          v10 (/(expt v 7.5)80640)
          v11 (/(expt v 9.5)6894720)
	  )
    (setq xn (* i (-(+(-(+(- v1 v2)v3)v4)v5)v6)))	  
    (setq yn (* i (+(-(+(- v7 v8)v9)v10)v11)))
    (command "color" 1)
    (command "point" (list xn yn))
    (if(= k 1);بداية تسجيل البيانات في حالة فرعين للكلوتوئيد وهي للفرع اليميني نفسها للفرع اليساري
		    (progn
		      (setq brx (list xn)
			    bry (list yn)
			    ldn (list ln)
			    t0x (list v)
			    )
		      )
		    (progn
		      (setq brx (append brx (list xn))
			    bry (append bry (list yn))
			    ldn (append ldn (list ln))
			    t0x (append t0x (list v))
		          )
		      
		        )
		    );نهاية تسجيل البيانا
    (setq k (+ 1 k))
    )
  )
(setq brx (append(list 0) brx))
(setq bry (append(list 0) bry))
(setq lbrx (length brx))
(setq lbry (length bry))
(command"spline"(list(nth 0 brx)(nth 0 bry))
(list(nth(fix(* 0.05 lbrx))brx)(nth(fix(* 0.05 lbrx))bry))	
(list(nth(fix(* 0.1 lbrx))brx)(nth(fix(* 0.1 lbrx))bry))
(list(nth(fix(* 0.15 lbrx))brx)(nth(fix(* 0.15 lbrx))bry))	
(list(nth(fix(* 0.2 lbrx))brx)(nth(fix(* 0.2 lbrx))bry))
(list(nth(fix(* 0.25 lbrx))brx)(nth(fix(* 0.25 lbrx))bry))	
(list(nth(fix(* 0.3 lbrx))brx)(nth(fix(* 0.3 lbrx))bry))
(list(nth(fix(* 0.35 lbrx))brx)(nth(fix(* 0.35 lbrx))bry))	
(list(nth(fix(* 0.4 lbrx))brx)(nth(fix(* 0.4 lbrx))bry))
(list(nth(fix(* 0.45 lbrx))brx)(nth(fix(* 0.45 lbrx))bry))	
(list(nth(fix(* 0.5 lbrx))brx)(nth(fix(* 0.5 lbrx))bry))
(list(nth(fix(* 0.55 lbrx))brx)(nth(fix(* 0.55 lbrx))bry))	
(list(nth(fix(* 0.6 lbrx))brx)(nth(fix(* 0.6 lbrx))bry))
(list(nth(fix(* 0.65 lbrx))brx)(nth(fix(* 0.65 lbrx))bry))	
(list(nth(fix(* 0.7 lbrx))brx)(nth(fix(* 0.7 lbrx))bry))
(list(nth(fix(* 0.75 lbrx))brx)(nth(fix(* 0.75 lbrx))bry))	
(list(nth(fix(* 0.8 lbrx))brx)(nth(fix(* 0.8 lbrx))bry))
(list(nth(fix(* 0.85 lbrx))brx)(nth(fix(* 0.85 lbrx))bry))	
(list(nth(fix(* 0.9 lbrx))brx)(nth(fix(* 0.9 lbrx))bry))
(list(nth(fix(* 0.95 lbrx))brx)(nth(fix(* 0.95 lbrx))bry))	
(list x0 y0) "" "" ""  )
  
   
  
(command "ucs" "world" )
(command "ucs" "New" "3p" st2 pc ps )
(command "point" (list x0 y0))
(setq k 1)
(setq n (/ l0 sn))
(while (<= k n)
  (progn
    (setq ln (* k sn))
    (setq v (/(expt ln 2)(expt i 2)))
    (setq v1 (expt v 0.5)
          v2 (/(expt v 2.5)10)
          v3 (/(expt v 4.5)216)
          v4 (/(expt v 6.5)9360)
          v5 (/(expt v 8.5)685440)
          v6 (/(expt v 10.5)76204800)
          v7 (/(expt v 1.5)3)
          v8 (/(expt v 3.5)42)
          v9 (/(expt v 5.5)1320)
          v10 (/(expt v 7.5)80640)
          v11 (/(expt v 9.5)6894720)
	  )
    (setq xn (* i (-(+(-(+(- v1 v2)v3)v4)v5)v6)))	  
    (setq yn (* i (+(-(+(- v7 v8)v9)v10)v11)))
    (command "color"1)
    (command "point" (list xn yn))
   (setq k (+ 1 k))
   )
  )
(setq brx (append(list 0) brx))
(setq bry (append(list 0) bry))
(setq lbrx (length brx))
(setq lbry (length bry))
(command"spline"(list(nth 0 brx)(nth 0 bry))
(list(nth(fix(* 0.05 lbrx))brx)(nth(fix(* 0.05 lbrx))bry))	
(list(nth(fix(* 0.1 lbrx))brx)(nth(fix(* 0.1 lbrx))bry))
(list(nth(fix(* 0.15 lbrx))brx)(nth(fix(* 0.15 lbrx))bry))	
(list(nth(fix(* 0.2 lbrx))brx)(nth(fix(* 0.2 lbrx))bry))
(list(nth(fix(* 0.25 lbrx))brx)(nth(fix(* 0.25 lbrx))bry))	
(list(nth(fix(* 0.3 lbrx))brx)(nth(fix(* 0.3 lbrx))bry))
(list(nth(fix(* 0.35 lbrx))brx)(nth(fix(* 0.35 lbrx))bry))	
(list(nth(fix(* 0.4 lbrx))brx)(nth(fix(* 0.4 lbrx))bry))
(list(nth(fix(* 0.45 lbrx))brx)(nth(fix(* 0.45 lbrx))bry))	
(list(nth(fix(* 0.5 lbrx))brx)(nth(fix(* 0.5 lbrx))bry))
(list(nth(fix(* 0.55 lbrx))brx)(nth(fix(* 0.55 lbrx))bry))	
(list(nth(fix(* 0.6 lbrx))brx)(nth(fix(* 0.6 lbrx))bry))
(list(nth(fix(* 0.65 lbrx))brx)(nth(fix(* 0.65 lbrx))bry))	
(list(nth(fix(* 0.7 lbrx))brx)(nth(fix(* 0.7 lbrx))bry))
(list(nth(fix(* 0.75 lbrx))brx)(nth(fix(* 0.75 lbrx))bry))	
(list(nth(fix(* 0.8 lbrx))brx)(nth(fix(* 0.8 lbrx))bry))
(list(nth(fix(* 0.85 lbrx))brx)(nth(fix(* 0.85 lbrx))bry))	
(list(nth(fix(* 0.9 lbrx))brx)(nth(fix(* 0.9 lbrx))bry))
(list(nth(fix(* 0.95 lbrx))brx)(nth(fix(* 0.95 lbrx))bry))	
(list x0 y0) "" "" ""  )
(command "ucs" "world" )
(setq ang3 (angle pc ps)
      ang4 (- pi ar)
      w (atan y0 (- s x0))
      q (-(/ ang4 2)w)
      )
(if (zerop q)
  (print "no curve")
  (progn
    (setq z (sqrt(+(expt(- s x0) 2)(expt y0 2)))
	  pm1 (polar pc (+ ang3 q) z)
	  pm2 (polar pc (- ang3 q) z)
	  )
    )
  );نهاية if
(command "point" (list pm1))
(command "point" (list pm2))
(command "color" 3)
(command "arc" (list (car pm1) (cadr pm1)) "e"(list(car pm2) (cadr pm2)) "radius" r0)
(setq angc (- ar (* 2 u)))
(setq angcg (/ (* angc 200)pi))
(setq lc (* angc r0))
(setq tx (polar pc 0 6))
(command "color"6)
(command "text"(polar pc 1.5708 6)"2" 100 "An=")
(command "text"(polar tx 1.5708 6)"2"100 (rtos a 2 4))
(command "text"(polar pc 1.5708 3)"2" 100 "dL=")
(command "text"(polar tx 1.5708 3)"2"100 (rtos sn 2 3))
(command "text" pc "2" 100 "l0=")
(command "text" tx "2" 100 (rtos l0 2 3))
(command "text"(polar pc -1.5708 3) "2" 100 "R0=")
(command "text"(polar tx -1.5708 3) "2" 100 (rtos r0 2 3))
(command "text"(polar pc -1.5708 6) "2" 100 "x0=")
(command "text"(polar tx -1.5708 6) "2" 100 (rtos x0 2 3))
(command "text"(polar pc -1.5708 9) "2" 100 "y0=")
(command "text"(polar tx -1.5708 9) "2" 100 (rtos y0 2 3))
(command "text"(polar pc -1.5708 12) "2" 100 "s=")
(command "text"(polar tx -1.5708 12) "2" 100 (rtos s 2 3))
(setq vm (/ (* v 200)pi))
(command "text"(polar pc -1.5708 15)"2" 100 "T0=")
(command "text"(polar tx -1.5708 15)"2" 100 (rtos t0 2 3))
(command "text"(polar pc -1.5708 18) "2" 100 "Ac=")
(command "text"(polar tx -1.5708 18) "2" 100 (rtos angcg 2 4))
(command "text"(polar pc -1.5708 21)"2" 100 "Lc=")
(command "text"(polar tx -1.5708 21)"2" 100 (rtos lc 2 3))
(setvar "osmode" oom)
(setvar"angbase"andb)
  (setvar "angdir"andr)
 (setvar"aunits"aunt)
    );نهاية العمليات الاولى اي نهاية عمليات الفرعين وبداية عمليات الفرع الواحد
	(progn
          
	  
	  (setq pc1 (getpoint "\n enter 1st point of circle")
		pc2 (getpoint "\n enter 2nd point of circle")
		pc3 (getpoint "\n enter 3rd point of circle")
		)
	  (setq G (/(+(car pc1)(car pc2))2)
		H (/(+(cadr pc1)(cadr pc2))2)
		I (/(+(car pc1)(car pc3))2)
		J (/(+(cadr pc1)(cadr pc3))2)
		M (-(car pc2)(car pc1))
		N (-(cadr pc2)(cadr pc1))
		O (-(car pc3)(car pc1))
		p (-(cadr pc3)(cadr pc1))
		A1 (*(* O M)I)
		A2 (*(* p M)J)
		A3 (*(* O M)G)
		A4 (*(* O N)H)
		A5 (-(* M p)(* O N))
		)
	  (setq A (-(-(+ A1 A2)A3)A4))
	  (setq Yc (/ A A5))
	  (setq Xc (/(+(-(* G M)(* N YC))(* N H))M))
	  (setq cc (list xc yc))
	  (setq r0 (sqrt(+(expt(- xc (car pc1))2)(expt (- yc (cadr pc1))2))))
(setq p1 (getpoint "\n enter the first point of line:")
      p2 (getpoint "\n enter the second point of line:")
      m1 (*(* (car p1)( cadr p2))(-( cadr p2)( cadr p1)))
      m2 (*(* (car p2)( cadr p1))(-( cadr p2)( cadr p1)))
      m3 (* xc (expt (-( car p1) ( car p2)) 2))
      m4 (*(*(-( car p1)(  car p2))(-( cadr p2)( cadr p1)))yc)
      m5 (+(expt(- (cadr p2)( cadr p1))2)(expt (-( car p1)( car p2))2))
      m (-(+(- m1 m2) m3)m4)
      x (/ m m5)
      t1 (* x (-(car p1)(car p2)))
      t2 (* yc(-(cadr p2)(cadr p1)))
      t3 (* xc(-(car p1)(car p2)))
      t4 (-(cadr p2)(cadr p1))
      y (/(-(+ t1 t2) t3) t4)
      ta (list x y)
)
	  (setq Dl (sqrt (+(expt(- xc x)2)(expt(- yc y)2))))
	  (setq D (- dl r0))
(setq m (expt(* 24 d r0)0.5)
      w (/ m(* 2 r0))
      i1 (sqrt (* m (* 2 r0)))
      w7 (/(expt w 1.5)3)
      w8 (/(expt w 3.5)42)
      w9 (/(expt w 5.5)1320)
      w10 (/(expt w 7.5)80640)
      w11 (/(expt w 9.5)6894720)
      z (* i1(+(-(+(- w7 w8)w9)w10)w11))
      e1 (* r0 (- 1 (cos w)))
      e (- z e1)
      n (+ 0.2 m)
      u (/ n (* 2 r0))
      i2 (sqrt (* n(* 2 r0)))
      u7 (/(expt u 1.5)3)
      u8 (/(expt u 3.5)42)
      u9 (/(expt u 5.5)1320)
      u10 (/(expt u 7.5)80640)
      u11 (/(expt u 9.5)6894720)
      y2 (* i2(+(-(+(- u7 u8)u9)u10)u11))
      f (- y2 (* r0(- 1 (cos u))))
      )
(setq l0 (/(+(* m(- f d))(* n(- d e)))(- f e)))
(setvar "osmode"0)
(setq u (/ l0(* 2 r0)))
(setq t0 (/(* 200 u)pi))
(princ "T0=")
(princ t0)
(setq i (sqrt(* 2(* l0 r0))))
(setq u1 (expt u 0.5)
      u2 (/(expt u 2.5)10)
      u3 (/(expt u 4.5)216)
      u4 (/(expt u 6.5)9360)
      u5 (/(expt u 8.5)685440)
      u6 (/(expt u 10.5)76204800)
      u7 (/(expt u 1.5)3)
      u8(/(expt u 3.5)42)
      u9 (/(expt u 5.5)1320)
      u10 (/(expt u 7.5)80640)
      u11 (/(expt u 9.5)6894720)
      )
(setq x0 (* i (-(+(-(+(- u1 u2)u3)u4)u5)u6)))
(setq y0 (* i (+(-(+(- u7 u8)u9)u10)u11))
      )
	 (initget "Right Left")
	  (setq q (getkword "\n define direction of kloto Right or Left:"))
	  (if(= q "Left")
	    (progn
	      (setq ang6 (angle cc ta)
		    c1 (polar cc(+ ang6 u)r0)
		    c2 (polar c1 ang6 y0)
		    cb (polar c2 (- ang6 (/ pi 2))x0)
		    cb1 (polar cb (- ang6 pi)200)
		    )
	      (command "point" (list (car c1)(cadr c1)))
	      (command "point" (list (car c2)(cadr c2)))
	      (command "point" (list (car cb)(cadr cb)))
	   (command "ucs" "new" "3p"  cb c2 cb1)
	      (setq k 1)
	      (setq sn (getreal "\n enter interval between points:")
		    n0 (/ l0 sn)
		    )
	      (while(<= k n0)
		(progn
		  (setq ln (* k sn)
			i (sqrt(* 2(* l0 r0))))
		 (setq v (/(expt ln 2)(expt i 2)))
                 (setq v1 (expt v 0.5)
                       v2 (/(expt v 2.5)10)
                       v3 (/(expt v 4.5)216)
                       v4 (/(expt v 6.5)9360)
                       v5 (/(expt v 8.5)685440)
                       v6 (/(expt v 10.5)76204800)
                       v7 (/(expt v 1.5)3)
                       v8 (/(expt v 3.5)42)
                       v9 (/(expt v 5.5)1320)
                      v10 (/(expt v 7.5)80640)
                      v11 (/(expt v 9.5)6894720)
	              )
    (setq xn (* i (-(+(-(+(- v1 v2)v3)v4)v5)v6)))	  
    (setq yn (* i (+(-(+(- v7 v8)v9)v10)v11)))
    (command "color"1)
    (command "point" (list xn yn))
(if(= k 1)
		    (progn
		      (setq brx (list xn)
			    bry (list yn)
			    ldn (list ln)
			    t0x (list v)
			    )
		      )
		    (progn
		      (setq brx (append brx (list xn))
			    bry (append bry (list yn))
			    ldn (append ldn (list ln))
			    t0x (append t0x (list v))
		          )
		        )
		    );ا اتمام تسجيل بيانات النقاط في حالة المنحني إلى اليسار		  
    (setq k (+ 1 k))
		 );نهاية progn الاخيرة
	      );نهاية whileالاخي
(setq brx (append(list 0) brx))
(setq bry (append(list 0) bry))
(setq lbrx (length brx))
(setq lbry (length bry))
(command"spline"(list(nth 0 brx)(nth 0 bry))
(list(nth(fix(* 0.05 lbrx))brx)(nth(fix(* 0.05 lbrx))bry))	
(list(nth(fix(* 0.1 lbrx))brx)(nth(fix(* 0.1 lbrx))bry))
(list(nth(fix(* 0.15 lbrx))brx)(nth(fix(* 0.15 lbrx))bry))	
(list(nth(fix(* 0.2 lbrx))brx)(nth(fix(* 0.2 lbrx))bry))
(list(nth(fix(* 0.25 lbrx))brx)(nth(fix(* 0.25 lbrx))bry))	
(list(nth(fix(* 0.3 lbrx))brx)(nth(fix(* 0.3 lbrx))bry))
(list(nth(fix(* 0.35 lbrx))brx)(nth(fix(* 0.35 lbrx))bry))	
(list(nth(fix(* 0.4 lbrx))brx)(nth(fix(* 0.4 lbrx))bry))
(list(nth(fix(* 0.45 lbrx))brx)(nth(fix(* 0.45 lbrx))bry))	
(list(nth(fix(* 0.5 lbrx))brx)(nth(fix(* 0.5 lbrx))bry))
(list(nth(fix(* 0.55 lbrx))brx)(nth(fix(* 0.55 lbrx))bry))	
(list(nth(fix(* 0.6 lbrx))brx)(nth(fix(* 0.6 lbrx))bry))
(list(nth(fix(* 0.65 lbrx))brx)(nth(fix(* 0.65 lbrx))bry))	
(list(nth(fix(* 0.7 lbrx))brx)(nth(fix(* 0.7 lbrx))bry))
(list(nth(fix(* 0.75 lbrx))brx)(nth(fix(* 0.75 lbrx))bry))	
(list(nth(fix(* 0.8 lbrx))brx)(nth(fix(* 0.8 lbrx))bry))
(list(nth(fix(* 0.85 lbrx))brx)(nth(fix(* 0.85 lbrx))bry))	
(list(nth(fix(* 0.9 lbrx))brx)(nth(fix(* 0.9 lbrx))bry))
(list(nth(fix(* 0.95 lbrx))brx)(nth(fix(* 0.95 lbrx))bry))	
(list x0 y0) "" "" ""  )
	      (command "ucs" "world")
	      (setq tx (polar cc 0 6))
	      (command "text" (polar cc 1.5708 3)"2"100 "D=")
	      (command "text"(polar tx 1.5708 3)"2"100 (rtos d 2 3))
	      (command "text" cc "2" 100 "l0=")
	      (command "text" tx "2" 100 (rtos l0 2 3))
	      (command "text" (polar cc -1.5708 3)"2" 100 "R0=")
	      (command "text" (polar tx -1.5708 3)"2" 100 (rtos r0 2 3))
	      (command "text" (polar cc -1.5708 6)"2" 100 "x0=")
	      (command "text" (polar tx -1.5708 6)"2" 100 (rtos x0 2 3))
	      (command "text" (polar cc -1.5708 9)"2" 100 "y0=")
	      (command "text" (polar tx -1.5708 9)"2" 100 (rtos y0 2 3))
	      (setq vf (/ l0 (* 2 r0)))
	      (setq vr (/ (* vf 200)pi))
	      (command "text"(polar cc -1.5708 12)"2" 100 "T0=")
	      (command "text"(polar tx -1.5708 12)"2" 100 (rtos vr 2 3))
	      (setvar "osmode"oom)
	      (setvar"angbase"andb)
              (setvar "angdir"andr)
              (setvar"aunits"aunt)
	      )
	      (progn;في حالة rightنفذ التعليمات التالية
		(setq ang6 (angle cc ta)
		    c1 (polar cc(- ang6 u)r0)
		    c2 (polar c1 ang6 y0)
		    cb (polar c2 (+ ang6 (/ pi 2))x0)
		    cb1 (polar cb (- ang6 pi)200)
		    )
	      (command "point" (list (car c1)(cadr c1)))
	      (command "point" (list (car c2)(cadr c2)))
	      (command "point" (list (car cb)(cadr cb)))
	   (command "ucs" "new" "3p"  cb c2 cb1)
	      (setq k 1)
	      (setq sn (getreal "\n enter interval between points:")
		    n0 (/ l0 sn)
		    )
	      (while(<= k n0)
		(progn
		  (setq ln (* k sn)
			i (sqrt(* 2(* l0 r0))))
		 (setq v (/(expt ln 2)(expt i 2)))
                 (setq v1 (expt v 0.5)
                       v2 (/(expt v 2.5)10)
                       v3 (/(expt v 4.5)216)
                       v4 (/(expt v 6.5)9360)
                       v5 (/(expt v 8.5)685440)
                       v6 (/(expt v 10.5)76204800)
                       v7 (/(expt v 1.5)3)
                       v8 (/(expt v 3.5)42)
                       v9 (/(expt v 5.5)1320)
                      v10 (/(expt v 7.5)80640)
                      v11 (/(expt v 9.5)6894720)
	              )
    (setq xn (* i (-(+(-(+(- v1 v2)v3)v4)v5)v6)))	  
    (setq yn (* i (+(-(+(- v7 v8)v9)v10)v11)))
    (command "color"1)
    (command "point" (list xn yn))
		  (if(= k 1)
		    (progn
		      (setq brx (list xn)
			    bry (list yn)
			    ldn (list ln)
			    t0x (list v)
			    )
		      )
		    (progn
		      (setq brx (append brx (list xn))
			    bry (append bry (list yn))
			    ldn (append ldn (list ln))
			    t0x (append t0x (list v))
		          )
		        )
		    );نهاية ifاللازمة لتشكيل بيانات النقاط 
		 (setq k (+ 1 k))
		 );نهاية progn الاخيرة
	);نهاية while
(setq brx (append(list 0) brx))
(setq bry (append(list 0) bry))
(setq lbrx (length brx))
(setq lbry (length bry))
(command"spline"(list(nth 0 brx)(nth 0 bry))
(list(nth(fix(* 0.05 lbrx))brx)(nth(fix(* 0.05 lbrx))bry))	
(list(nth(fix(* 0.1 lbrx))brx)(nth(fix(* 0.1 lbrx))bry))
(list(nth(fix(* 0.15 lbrx))brx)(nth(fix(* 0.15 lbrx))bry))	
(list(nth(fix(* 0.2 lbrx))brx)(nth(fix(* 0.2 lbrx))bry))
(list(nth(fix(* 0.25 lbrx))brx)(nth(fix(* 0.25 lbrx))bry))	
(list(nth(fix(* 0.3 lbrx))brx)(nth(fix(* 0.3 lbrx))bry))
(list(nth(fix(* 0.35 lbrx))brx)(nth(fix(* 0.35 lbrx))bry))	
(list(nth(fix(* 0.4 lbrx))brx)(nth(fix(* 0.4 lbrx))bry))
(list(nth(fix(* 0.45 lbrx))brx)(nth(fix(* 0.45 lbrx))bry))	
(list(nth(fix(* 0.5 lbrx))brx)(nth(fix(* 0.5 lbrx))bry))
(list(nth(fix(* 0.55 lbrx))brx)(nth(fix(* 0.55 lbrx))bry))	
(list(nth(fix(* 0.6 lbrx))brx)(nth(fix(* 0.6 lbrx))bry))
(list(nth(fix(* 0.65 lbrx))brx)(nth(fix(* 0.65 lbrx))bry))	
(list(nth(fix(* 0.7 lbrx))brx)(nth(fix(* 0.7 lbrx))bry))
(list(nth(fix(* 0.75 lbrx))brx)(nth(fix(* 0.75 lbrx))bry))	
(list(nth(fix(* 0.8 lbrx))brx)(nth(fix(* 0.8 lbrx))bry))
(list(nth(fix(* 0.85 lbrx))brx)(nth(fix(* 0.85 lbrx))bry))	
(list(nth(fix(* 0.9 lbrx))brx)(nth(fix(* 0.9 lbrx))bry))
(list(nth(fix(* 0.95 lbrx))brx)(nth(fix(* 0.95 lbrx))bry))	
(list x0 y0) "" "" ""  )
		(command "ucs" "world")
		(setq tx (polar cc 0 6))
		(command "text" (polar cc 1.5708 3)"2"100 "D=")
	      (command "text"(polar tx 1.5708 3)"2"100 (rtos d 2 3))
	      (command "text" cc "2" 100 "l0=")
	      (command "text" tx "2" 100 (rtos l0 2 3))
	      (command "text" (polar cc -1.5708 3)"2" 100 "R0=")
	      (command "text" (polar tx -1.5708 3)"2" 100 (rtos r0 2 3))
	      (command "text" (polar cc -1.5708 6)"2" 100 "x0=")
	      (command "text" (polar tx -1.5708 6) "2" 100 (rtos x0 2 3))
	      (command "text" (polar cc -1.5708 9) "2" 100 "y0=")
	      (command "text" (polar tx -1.5708 9) "2" 100 (rtos y0 2 3))
	      (setq vc (/ l0(* 2 r0)))
	      (setq vx (/(* vc 200)pi))
	      (command "text" (polar cc -1.5708 12) "2" 100 "T0=")
	      (command "text" (polar tx -1.5708 12) "2" 100 (rtos vx 2 3))
	      
	      (setvar "osmode"oom)
	      (setvar"angbase"andb)
              (setvar "angdir"andr)
              (setvar"aunits"aunt)	
		
		  )
	      )
	    )
	  )
              (setvar "osmode"oom)
	      (setvar"angbase"andb)
              (setvar "angdir"andr)
              (setvar"aunits"aunt)
  )
