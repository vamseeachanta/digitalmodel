(defun c:2(/ pt1 pt2 north east)
(setvar "cmdecho" 0)
(setq pt1 (getpoint "\nPick point :"))
(setq pt2 (getpoint pt1 "\nPick Text location :"))
 (setq north (rtos (/ (cadr pt1) 1) 2 3))
 (setq east (rtos (car  pt1) 2 3))
 (command "leader" pt1 pt2 "a" north east "")
 (princ)
)
