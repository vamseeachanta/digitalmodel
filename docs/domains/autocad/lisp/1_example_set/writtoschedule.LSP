;الخرائط الطبوغرافيه تكون عادة منسوبه الى جملة احداثيات ومن المعلومات التي نحتاجها من الخريطه
;احداثيات نقاطها يتم الحصول على هذه الأحداثيات عادة بالنقر على النقطه أو أي عنصر لأظهار نقاط
;تظهر الاحداثيات في سطر المعلومات ليتم نقلها يدويا osnap الإمساك ثم الإشاره اليها او عن طريق
;تعتبر هذه الطريقه غير عمليه في حال وجود كم كبير من النقاط مع احتمال ارتكاب الأخطاء اثناء النقل
;أما البرنامج المرفق فيقوم بقراءة احداثيات هذه النقاط وتسجيلها ضمن جدول يتم تحديد نقطة إدراجه
;على الشاشه وذلك بالنقر على النقطه المراد تسجيل احداثياتها  في الجدول ثم اعطاء اسمها فتكتب
;الأحداثيات مع الأسم وهكذا يتم التكرار حتى يتم الضغظ على زر الهروب
;ولتنفيذ البرنامج ماعليك سوى نسخه ولصقه في محرر اوتولسب من قائمة ادوات
;.lsp لا يهم اذا نسخت الشرح واحفظ الملف باسم معين في مكان معين وبامتداد 
;ومن القائمه ادوات افتح تحميل تطبيقات تظهر النافذه تحميل افتح حقيبة الاقلاع ثم اضف مسار الملف
;الذي  حفظته من قبل لكي يكون متوفرا في كل الجلسات
(defun c:writ (/ p1 p2 p3 p01 p11 p21 p31 pn px	py ip in p02 p0n p12 p0x
	       p22 p0y p32)

;بحيث يتم ادخاله وتنفيذه عن طريق كتابته في سطر الأوامر writ يعني اننا عرفنا الأمر  defun c: الأمر
;الخ سيتم حذف قيمتهامن الذاكره بعد تنفيذ البرنامج... p1 p2 p3 p01  وأن المتحولات اللاحقه 
  (setq	p0  (getpoint "\n enter uper left of schedule")
;p0 ويخزن احداثياتها في النقطه getpoint هنا يسألك البرنامج عن نقطة ادراج الجدول عن طريق الأمر 
;setq عن طريق الأمر
;نقوم هنا بحساب نقاط الجدول استنادا الى نقطة الأدراج	
	p1  (list (+ (car p0) 5) (cadr p0))
;y والثانيه الإحداثي x هنا نقوم بتشكيل لوائح كل لائحه مكونه من قيمتين القيمه الأولى هي الإحداثي
;y وقيمه الى  x وكل لائحه هي نقطه وكل نقطه مستنتجه من اخرى بإضافة قيمه الى
;هي عباره عن لائحه القيمه الأولىفيها p1 وبناءً عليه يقرأ التعبير السابق بأن النقطه
;p0 مضافا اليها القيمه خمس وحدات والقيمه الثانيه نفسها للنقطه p0 هي الإحداثي الأول للنقطه
;تعني العنصر الثاني cadr تعني العنصر الأول و car أي أن 	
	p2  (list (+ (car p0) 12) (cadr p0))
	p3  (list (+ (car p0) 19) (cadr p0))
	p01 (list (car p0) (- (cadr p0) 2))
	p11 (list (car p1) (- (cadr p1) 2))
	p21 (list (car p2) (- (cadr p2) 2))
	p31 (list (car p3) (- (cadr p3) 2))
	pn  (list (+ (car p0) 1.5) (- (cadr p0) 1.2))
	px  (list (+ (car p1) 2.5) (- (cadr p1) 1.2))
	py  (list (+ (car p2) 2.5) (- (cadr p2) 1.2))
  )
  (setvar "osmode" 0)			;القيمه صفر وذلك لكي لا يتم الإدراج في نقاط غير محدده osnap إعطاء متغير النظام 
  (setvar "angdir" 1)			;تبديل اعدادات اوتوكاد بحيث يصبح تزايد الزوايا  مع عقارب الساعه
  (setvar "angbase" 1.5708)		;تبديل مبدأ الزاويا بحيث يصبح من أعلى الخريطه أي الشاشه
  (setvar "aunits" 2)			;تبديل قياس الزوايا الى النظام المئوي أي الغراد
  (command "rectang" p0 p11)		;رسم مستطيل
  (command "rectang" p1 p21)
  (command "rectang" p2 p31)
  (command "text" pn "0.7" 100 "N")
; والمقياس0.7 وزاوية الدوران 100 غراد pn نقطة الإدراج هي  N كتابة النص 
  (COMMAND "text" px "1" 100 "X")
  (COMMAND "text" py "1" 100 "y")
  (setvar "osmode" 553)
  (while (setq ip  (getpoint "\n enter a point to write its coordinate")
;قراءة الاحداثيات
	       in  (getstring "\n enter name of this point")
;اسم النقطه
	       p02 (list (car p01) (- (cadr p01) 2))
	       p0n (list (+ (car p02) 0.3) (+ (cadr p02) 0.3))
	       p12 (list (+ (car p01) 5) (- (cadr p01) 2))
	       p0x (list (+ (car p12) 0.5) (+ (cadr p12) 0.3))
	       p22 (list (+ (car p01) 12) (- (cadr p01) 2))
	       p0y (list (+ (car p22) 0.5) (+ (cadr p22) 0.3))
	       p32 (list (+ (car p01) 19) (- (cadr p01) 2))
	 )
    (setvar "osmode" 0)
    (command "color" 1)
    (command "rectang" p01 p12)
    (command "rectang" p11 p22)
    (command "rectang" p21 p32)
    (command "color" 3)
    (command "text" p0n "1" 100 in)
    (command "color" 5)
    (command "text" p0x "0.6" 100 (rtos (car ip) 2 3))
;في النظام العشري وبدقة ثلاث ارقام بعد الفاصله x كتابة الاحداثي 
    (command "text" p0y "0.6" 100 (rtos (cadr ip) 2 3))
;y كتابة الاحداثي 
    (setvar "osmode" 553)
    (setq p01 p02
    )
  )
)
;;writ بعد القيام بالعمليات السابقه اكتب في سطر الأوامر الأمر
;فيتم البدء بتنفيذ البرنامج فيسألك أولاً عن نقطة إدراج الجدول أختر أي نقطه على الشاشه
; N   X     Y قتظهر لك ثلاث  خلايا كتب فيها على التسلسل 
;ثم تسأل عن  النقطه التي تود تسجيل احداثياتها في الجدول انقر عليها ثم تسأل عن اسمها
;فيتم تسجيل  النتائج في الجدول
;وهكذا حتى الأنتهاء
;ملاحظه هامه الى الزملاء المعماريين
;يكون الرسم المعماري ذو فائده عظيمه إذا تم رسمه ضمن شبكة احداثيات
;فهذا يسهل عملية اسقاطه على الطبيعه مهما كان معقداً لأن الطبوغرافي إذا زود بالأحداثيات يصبح كل
;شيء محلولاً
