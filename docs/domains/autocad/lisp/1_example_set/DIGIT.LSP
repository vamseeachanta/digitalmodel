(defun C:ADIG ()
(defun *error* (msg)
	(princ "error: ")
	(princ msg)
	(terpri)
)
	(setq digfil (getvar "dwgname"))
	(graphscr)
	(setq ext ".mcr"
		dext ".dwg"
		dfil (strcat digfil ext)
		sdfil (strcat digfil)
		dwgfil (strcat digfil dext)
	)
	(setvar "cmdecho" 1)
	(setq ans (findfile dwgfil))
	(IF (= ANS nil)
		(progn
			(command "tablet" "cal" pause pause)
			(setq pt3 (getpoint "\nDIGITIZE LOWER LEFT CORNER:")
				pt4 (getpoint "\nDIGITIZE UPPER RIGHT CORNER:")
			)
			(setq lmfil (open "limits.tmp" "w"))
			(princ pt3 lmfil)
			(princ "\n" lmfil)
			(princ pt4 lmfil)
			(close lmfil)
			(setvar "cmdecho" 0)
			(command "LAYER" "MAKE" "TRANS" "")
			(command "layer" "MAKE" "LABEL" "")
			(command "LAYER" "MAKE" "AREA"  "")
			(command "LAYER" "MAKE" "GRID" "")
			(command "LAYER" "MAKE" "ANNO" "")
			(command "LAYER" "MAKE" "DIST" "")
			(command "LAYER" "SET" "0" "" "c" 4 "" "")
			(command "limits" pt3 pt4
				"zoom" "a"
				"osnap" "none"
				"ucsicon" "off"
			)
			(setvar "pdmode" 32)
			(setvar "pdsize" 7)
			(command "color" "bylayer")
		)
	)
	(command "tablet" "on")
	(if (= ans "YES") (setq f (open dfil "w")))
		(setq f (open dfil "a"))
		(prompt "\nSHEET NAME IS:")
		(prompt digfil)
		(PROMPT "\nDIGITIZING PROCESS STARTED... ")
		(setq alp (getpoint "\nDIGITIZE FIRST POINT:"))
		(setq x (car alp)
			y (cadr alp)
			x (rtos x 2 4)
			y (rtos y 2 4)
		)
			(princ "(" f)
			(princ x f)
			(princ " " f)
			(princ y f)
			(princ ")" f)
			(princ "\n" f)
			(command "point" alp)
			(SETQ AL 0)
		(IF (/= AL NIL)
			(PROGN
				(WHILE (setq al (getpoint "\nDIGITIZE NEXT POINT:"))
		(setq x0 (car al)
			y0 (cadr al)
			x0 (rtos x0 2 4)
			y0 (rtos y0 2 4)
		)
			(princ "(" f)
			(princ x0 f)
			(princ " " f)
			(princ y0 f)
			(princ ")" f)
			(princ "\n" f)
		(command "point" al
			"line" alp al
			""
		)
		(setq alp al)
				)
			)
		)
(close f)
		(command "tablet" "off")
		(setq dtemp (getvar "dwgprefix"))
		(setq temp (strcat dtemp "temp0000"))
		(command "save" temp "Y")
		(command "save" sdfil "Y")
)
