(defun rtd (a) (/ (* a 180.0) pi))
(defun c:idtab()
       (setq h (getdist "\nEnter height of text:"))
       (setq ha (getangle "\nEnter two point to show the Horizontal angle:"))
       (setq va (getangle "\nEnter two point to show the vertical angle:"))
       (setq ds1 (getdist "\nEnter width of 1st colum:"))
       (setq ds2 (getdist "\nEnter width of 2nd colum:"))
       (setq ds3 (getdist "\nEnter height of Row:"))
       (setq bs (getpoint "\nEnter Base point:"))
       (setq b (getpoint "\nEnter start point:"))
       (setq lm 0)
       (setq bs1 (polar bs ha ds1))
       (setq bs2 (polar bs ha (+ ds1 ds2)))
       (command "layer" "n" "table" "c" "7" "table" "")
       (command "layer" "s" "table" "")
       (command "units" 2 3 2 4 0 N)

  (while b
       (SETQ KK (POLAR B (+ VA PI) H))
       (setq st (polar bs va (* ds3 lm)))
       (setq st1 (polar bs1 va (* ds3 lm)))
       (setq st2 (polar bs2 va (* ds3 lm)))
       (COMMAND "TEXT" KK H (RTD HA) (+ 1 LM))
       (command "text" st h (rtd ha) (+ 1 LM))
       (command "text" st1 h (rtd ha) (rtos (car b)))
       (command "text" st2 h (rtd ha) (rtos (cadr b))) 
       (setq lm (+ lm 1))
       (setq b (getpoint "\nEnter next point:"))
       )   
  )
