(vl-load-com)

(defun c:ArtL()
	(cre_lay "CurveLines" 3)
	(setq acSet(ssget (list (cons 0 "Circle,Arc"))))
	(if (/= acSet nil)
		(progn
			(setq cntr 0)
			(setq acLen(sslength acSet))
			(repeat acLen
				(setq wEnt(ssname acSet Cntr))
				(arctopoints wEnt)
				(setq pntCntr 0)
				(command "._Pline")
				(repeat (length pntList)
					(command (nth pntCntr pntList))
					(setq pntCntr(1+ pntCntr))
				)
				(command "")
				(command "._Change" (entlast) "" "p" "layer" "CurveLines" "")
				(setq cntr(1+ cntr))
			)
		)
	)
	(alert (strcat "\nProgram Developed by ESurveying Softech (India) Pvt. Ltd." "\nContact: +91 9449599709" "\nEmail: [email removed]" "\nWebSite: www.esurveying.net"))
	(princ)
)
(princ "\nType \"ArtL\" to Split Arc or Circles as Series of Lines.") (princ)

;Function to Find out Vertexs along Given Arc / Circle.
(defun arctopoints(curEnt)
	(setq obj(vlax-ename->vla-object curEnt))
	(setq eType(vla-get-objectname obj))
	(if (= eType "AcDbArc")
		(setq divNum 12)
		(setq divNum 24)
	)
	(setq pntList '())
	(if (= eType "AcDbArc")
		(setq divFact (/ (setq leng (vla-get-arclength obj)) divNum))
		(setq divFact (/ (setq leng (vla-get-circumference obj)) divNum))
	)
	(setq constFact divFact)
	(setq cnt 0)
	(repeat (1+ divNum)
		(if (= cnt divNum)
			(if (= eType "AcDbArc")
				(setq curPoint (vlax-curve-getEndPoint obj))
				(setq curPoint (vlax-curve-getStartPoint obj))
			)
			(setq curPoint (vlax-curve-getclosestpointto obj (vlax-curve-getpointatdist obj (* constFact cnt))))
		)
		(setq pntList(append pntList (list curPoint)))
		(setq cnt (1+ cnt))
		(setq divFact(+ divFact constFact))
	)
	(setq return pntList)
)

;Function to Create a Layer with given color
(defun Cre_Lay(lay_layn lay_laycol)
	(if (= (tblsearch "Layer" lay_layn) nil)
		(command "._Layer" "n" lay_layn "c" lay_laycol lay_layn "")
		(command "._Layer" "t" lay_layn "on" lay_layn "c" lay_laycol lay_layn "")
	)
	(princ)
)
