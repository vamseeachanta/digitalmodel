;;; By Jimmy Bergmark
;;; Copyright (C) 1997-2006 JTB World, All Rights Reserved
;;; Website: www.jtbworld.com
;;; E-mail: [email removed]

;;; Plot dialog by lisp
(defun c:plotdialog()
  (initdia)
  (command "._plot")
)
