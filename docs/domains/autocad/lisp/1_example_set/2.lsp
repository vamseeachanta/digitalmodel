(defun c:2 ()
(setq osm (getvar "osmode"))
(setvar "osmode" 0)
  (setq sp (getpoint "\nPick the start point of the cahnnel"))
  (setq width (getreal "\nWhat is the width of the channel"))
  (setq thk1 (getreal "\nWhat is the thickness of the channel width"))
  (setq hgt (getreal "\nWhat is th height of the channel"))
  (setq thk2 (getreal "\nWhat is the thickness of channel walls"))
  (setq rad (getreal "\nWhat is the interior radius"))
  (setq x1 (car sp)
	x2 (+ x1 thk1)
	x3 (+ x2 rad)
	x4 (+ x1 hgt)
	y1 (cadr sp)
	y2 (+ y1 thk2)
	y3 (+ y2 rad)
	y6 (+ y1 width)
	y5 (- y6 THK2)
	y4 (- y5 rad)
)
  (setq p1 (list x1 y1)
	p2 (list x4 y1)
	p3 (list x4 y2)
	p4 (list x3 y2)
	p5 (list x2 y3)
	p6 (list x2 y4)
	p7 (list x3 y5)
	p8 (list x1 y6)
	p9 (list x4 y5)
	p10 (list x4 y6)
	)
  (command "line" p1 p2 "")
  (command "line" p2 p3 "")
  (command "line" p3 p4 "")
  (command "line" p5 p6 "")
  (command "line" p7 p9 "")
  (command "line" p9 P10 "")
  (command "line" p10 p8 "")
  (command "line" p8 p1 "")
  (command "arc" p5 "e" p4 "r" rad)
  (command "arc" p7 "e" p6 "r" rad)
  (setvar "osmode" osm)
  )
