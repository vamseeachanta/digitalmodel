;قد تضطر أحياناً لجمع أرقام موجوده على الشاشه أمامك
;فإنه من الأفضل أن تقوم بعملية الجمع بشكل مباشر بدون الاستعانه بالآله الحاسبه
;ماعليك سوى  ان تنقر على الرقم مع زر الادخال فترى الرقم في سطر الحاله تنقر على الرقم الثاني مع
;زر الادخال ترى المجموع  وهكذا حتى تتوقف عن الادخال
; add لتشغيل البرنامج حمله ثم اكتب 
(defun c:add ()
(setq sum (list + ))
  (while
    (setq pt1 (ssget))
    (Setvar "osmode" 0)
    (setq oldelem (entget (ssname pt1 0)))      
  (setq txtstr (assoc 1 oldelem))
  (setq num (atof(cdr txtstr)))                                       
  (setq sum (append sum (list num)))
  (terpri)
  (princ num)
  (terpri)
  (princ "total=")
  (princ (rtos(eval sum)2 3))
   )
  )
