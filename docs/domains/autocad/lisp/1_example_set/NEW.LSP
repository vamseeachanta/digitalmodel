(defun c:ZX()
	(setvar "cmdecho" 0)
	(command "ZOOM" "P")
	(princ)
)

(defun c:ZD()
	(setvar "cmdecho" 0)
	(command "ZOOM" "D")
	(princ)
)

(defun c:ZA()
	(setvar "cmdecho" 0)
	(command "ZOOM" "ALL")
	(princ)
)

(defun C:SACH ()
  (setq m:err *error* *error* *merrmsg*)
  (setq Name (getvar "DWGNAME"))
  (COMMAND "WBLOCK" Name "Y" "" "0,0" "ALL" "" "Open" "y" Name)
  (setq *error* m:err m:err nil)
  (princ)
)

(defun C:NC ()
  (setq m:err *error* *error* *merrmsg*)
  (COMMAND "SH" "NC")
  (setq *error* m:err m:err nil)
  (princ "\n               Hen gap lai ...! ")
  (princ)
)

(defun C:sdr ()
  (setq m:err *error* *error* *merrmsg*)
  (COMMAND "sdr0" " ")
  (setq *error* m:err m:err nil)
  (princ)
)

(defun c:ng()
	(setvar "cmdecho" 0)
	(princ "\n Cho 2 diem gan nhat de ngieng ..... ")
	(command "ucs" "z" "nea" pause "nea" pause)
	(princ)
)

(defun c:nn()
	(setvar "cmdecho" 0)
	(command "ucs" "")
	(princ)
)

(defun C:EE ()
  (Setvar "cmdecho" 0) 
  (set_style "Romans" 0)      
  (COMMAND ".ERASE" "P" "")
  (princ)
)

(defun C:BR ()
  (Setvar "cmdecho" 0) 
  (while (/= (setq sset (entsel "\nSelect object to break:")) nil)
	(COMMAND ".BREAK" sset  "F" "_int" pause "@")
  )
  (princ)
)

;;;========COMMAND FOR DIM ====

;---------------
(defun C:XY ()
  (Setvar "cmdecho" 0) 
  (setq m:err *error* *error* *merrmsg*)
  (prompt"\nChon Dimension: ")
  (setq set (ssget))
  (if (null set) (exit))
  (if (null P1) (setq P1 '(0 0 0)))
  (setq _P1 (getpoint (strcat "\nVi tri moi cua Dimension <vi tri cu: " (rtos (car P1) 2 2) "," (rtos (cadr P1) 2 2) ">: ")))
  (if (/= _P1 nil) (setq P1 _P1))
  (setq X3 (car P1))
  (setq Y3 (cadr P1))
  (command "ucs" "O" P1)
  (if (null EX) (setq EX 10))
  (setq _EX (getreal (strcat "\nDo dai can thiet(- Trai=Tren + Phai=Duoi) <" (rtos EX 2 1) ">: ")))
  (if (/= _EX nil) (setq EX _EX))
  (setq X4 (+ X3 EX))
  (setq Y4 (- Y3 EX))
  (setq quant (sslength set))
  (setq index 0)
 (While (< index quant)
	(If (and (= "DIMENSION" (cdr (assoc 0 (setq A (entget (ssname set index ))))))
	    )
	 (progn
			(setq L13 (assoc 13 A))
			(setq M13 (cdr L13))
			(setq L14 (assoc 14 A))
			(setq M14 (cdr L14))     
			(setq L10 (assoc 10 A))
			(setq M10 (cdr L10))
			(setq L50 (assoc 50 A))
			(setq M50 (cdr L50))
		(if (/= M50 0.0)
		   (progn       
			(setq P13 (list 13 X3 (cadr M13) (caddr M13)))
			(setq A (subst P13 L13 A))
			(setq P14 (list 14 X3 (cadr M14) (caddr M14)))
			(setq A (subst P14 L14 A))
			(setq P10 (list 10 X4 (cadr M10) (caddr M10)))
			(setq A (subst P10 L10 A))
			(Entmod A)
		   ) ;;{Progn} 
		)  ;;{If}
		(if (= M50 0)
		   (progn       
			(setq P13 (list 13 (car M13) Y3 (caddr M13)))
			(setq A (subst P13 L13 A))
			(setq P14 (list 14 (car M14) Y3 (caddr M14)))
			(setq A (subst P14 L14 A))
			(setq P10 (list 10 (cadr M10) Y4 (caddr M10)))
			(setq A (subst P10 L10 A))
			(Entmod A)
		   ) ;;{Progn} 
		)  ;;{If}
	 ) ;;{progn}
	) ;;{If}        
	(setq index (+ index 1))
  (Command "_dim1" "_Home" set "")
 );; {While}            
  (command "ucs" "w")
  (setq *error* m:err m:err nil)
  (prompt "\nBye ! See you again.")
  (princ)
)
;---------------

(defun C:al()
  (Setvar "cmdecho" 0) 
  (set_style "Romans" 0)      
  (COMMAND "_DIM1" "_ali")
  (princ)
)

(defun C:H ()
  (Setvar "cmdecho" 0) 
  (set_style "Romans" 0)      
  (COMMAND "_DIM1" "_HOR")
  (princ)
)

(defun C:V ()
  (Setvar "cmdecho" 0) 
  (set_style "Romans" 0)      
  (COMMAND "_DIM1" "_VER")
  (princ)
)

(defun C:N ()
  (Setvar "cmdecho" 0) 
  (set_style "Romans" 0)      
  (COMMAND "_DIM1" "_NEW")
  (princ)
)

(defun C:CO ()
  (Setvar "cmdecho" 0) 
  (set_style "Romans" 0)      
  (COMMAND "_DIM1" "_CO")
  (princ)
)


(defun c:up()
	(setvar "cmdecho" 0)
        (set_style "Romans" 0)      
	(princ "\n DIM to update ?  ")
	(command "dim1" "update" pause)
	(princ)
)

;;;====================================
(defun C:O ()
 (Setvar "cmdecho" 0) 
 (setq m:err *error* *error* *merrmsg*)
 (if (null TL) (setq TL 100))
 (initget 6)
 (setq _TL (getreal (strcat "\nTi le can ve <1/" (rtos TL 2 1) ">: ")))
 (if (/= _TL nil) (setq TL _TL))
 (if (null KC) (setq KC 1.0))
 (setq _KC (getreal (strcat "\nKhoang cach offset <" (rtos KC 2 1) ">: ")))
 (if (/= _KC nil) (setq KC _KC))
 (setq off (/ KC TL))

 (princ "\n Select object to offset ")
 (command "_offset" off pause)
 (setq *error* m:err m:err nil)
 (princ)
)


;;;==== COMMAND FOR POLYLINE ==========
(defun C:fd (
/  ps1  ps2  pf1  pf2  pf3  pf4  pf5  pf6
   pf7  pf8  sb   sh   se   ang  old_osmode)
;   (setq old_osmode (getvar "OSMODE"))
   (setq ps1 (getpoint "\nPick first point: "))
   (setq ps2 (getpoint ps1 "\nPick second point: "))
   (setq sb 2.0 sh 4.0 se 2.0)
   (setq ang (angle ps1 ps2))
   (setq pf1 (polar ps1 ang (- 0.0 se)))
   (setq pf2 (polar ps1 ang (/ (- (distance ps1 ps2) sb) 2.0) ))
   (setq pf7 (polar pf2 ang (/ sb 3.0)))
   (setq pf3 (polar pf7 (+ ang (/ pi 2)) (/ sh 2.0)))
   (setq pf8 (polar pf7 ang (/ sb 3.0)))
   (setq pf4 (polar pf8 (- ang (/ pi 2)) (/ sh 2.0)))
   (setq pf5 (polar pf8 ang (/ sb 3.0)))
   (setq pf6 (polar ps2 ang se))
   (setvar "OSMODE" 0)
   (setvar "BLIPMODE" 0)
   (command "LINE" pf1 pf2 pf3 pf4 pf5 pf6 "")
   (setvar "OSMODE" 177)
   (setvar "BLIPMODE" 1)
   (princ)
   )
;;=============================================================================
(defun C:DF (
/  ps1  ps2  pf1  pf2  pf3  pf4  pf5  pf6
   pf7  pf8  sb   sh   se   ang  old_osmode)
;   (setq old_osmode (getvar "OSMODE"))
   (setq ps1 (getpoint "\nPick first point: "))
   (setq ps2 (getpoint ps1 "\nPick second point: "))
   (setq sb 2.5 sh 3.5 se 1.0)
   (setq ang (angle ps1 ps2))
   (setq pf1 (polar ps1 ang (- 0.0 se)))
   (setq pf2 (polar ps1 ang (/ (- (distance ps1 ps2) sb) 2.0) ))
   (setq pf3 (polar pf2 (+ ang (/ pi 2)) (/ sh 2.0)))
   (setq pf5 (polar pf2 ang sb))
   (setq pf4 (polar pf5 (- ang (/ pi 2)) (/ sh 2.0)))
   (setq pf6 (polar ps2 ang se))
   (setvar "OSMODE" 0)
   (setvar "BLIPMODE" 0)
   (command "LINE" pf1 pf2 pf3 pf4 pf5 pf6 "")
   (setvar "OSMODE" 177)
   (setvar "BLIPMODE" 1)
   (princ)
   )

(defun C:J ()
 (Setvar "cmdecho" 0) 
 (setq m:err *error* *error* *merrmsg*)
 (setq sset (ssget))
 (if (null sset) (exit))
 (setq kt (getstring "\nJoin all (Y/N) <Y> ? "))
 (setq ssl (sslength sset))
 (setq temp  (entget (ssname sset 0))
       etype (cdr (assoc 0 temp))
 )
(cond
 ((or (= kt "Y") (= kt "y") (= kt ""))
  (progn
   (cond
	((= etype "POLYLINE")   
	    (COMMAND "PEDIT" sset "J" "all" "" "")
	)  
	(if (or (= etype "LINE") (= etype "ARC"))
	    (COMMAND "PEDIT" sset "" "J" "all" "" "")
	)
   )
  )
 )
 ((or (/= kt "Y") (/= kt "y") (/= kt ""))
  (progn
    (cond
	((= etype "POLYLINE")   
	    (COMMAND "PEDIT" sset "J" sset "" "")
	)  
	(if (or (= etype "LINE") (= etype "ARC"))
	    (COMMAND "PEDIT" sset "" "J" sset "" "")
	)  
     )
  )
 )
)
 (setq *error* m:err m:err nil)
 (princ)
)


(defun c:W()
 (Setvar "cmdecho" 0)
 (setq m:err *error* *error* *merrmsg*)
 (setq sset (ssget))
 (if (null sset) (exit))
 (if (null Rong) (setq Rong 3.0))
 (setq _Rong (getreal (strcat "\nBe day cua Polyline <" (rtos Rong 2 1) ">: ")))
 (if (/= _Rong nil) (setq Rong _Rong))
 (if (> Rong 10) (setq Rong (/ rong 10)))
 (if (> Rong 1) (setq Rong (/ rong 10)))
 (setq ssl (sslength sset) _ssl 0)
 (while (> ssl 0)
  (setq temp (ssname sset (setq ssl (1- ssl))))
  (setq lname (cdr (assoc 0 (entget temp))))
  (if (or (= lname "LINE") (= lname "ARC") (= lname "POLYLINE") (= lname "CIRCLE"))
    (progn
	 (cond
	  ((= lname "POLYLINE")
	   (command "PEDIT" temp "w" Rong "")
	  )
	  ((= lname "CIRCLE")
	   (setq cen (cdr (assoc 10 (entget temp)))
		 rad (cdr (assoc 40 (entget temp)))
	   )
	   (command "ERASE" temp "" "PLINE" (list (+ (car cen) rad) (cadr cen))
		    "W" rong rong "A" "CE" cen "A" 180 "CE" cen "A" 180 "")
	  )
	  (if (or (= lname "LINE") (= lname "ARC"))
	      (command "PEDIT" temp "" "w" rong "")
	  )
	 )      
	(setq _ssl (1+ _ssl))
	(redraw temp 1)
    )
  )
 )
 (princ _ssl)
 (princ " object(s) were changed.")
 (setq *error* m:err m:err nil)
 (princ)
)
(princ"\n Cam on ban da su dung chuong trinh nay.")
(princ)

(DEFUN C:AA ( / p1 p2 p3  p4 pp1 pp2 x1 x2 x3 y1 y2 y3 txt
		a1 a2 a3 ap dis)
  (setq p1 (getpoint "\nPick first  origin point : "))
  (setq p2 (getpoint p1 "\nPick second origin point : "))
  (setq p3 (getpoint "\nExtension point : "))
  (setq a1 (angle p1 p2))
  (setq a2 (angle p1 p3))
  (setq ap (- (- a1 (/ PI 2)) a2))
  (setq dis (* (distance p1 p3) (cos ap)))
  (setq pp1 (polar p1 (- a1 (/ PI 2)) dis))
  (setq pp2 (polar pp1 a1 (distance p1 p2)))  
  (setvar "OSMODE" 0)
  (setvar "BLIPMODE" 0)
  (COMMAND "DIM1" "ALI" pp1 pp2 )
  (setvar "OSMODE" 177)
  (setvar "BLIPMODE" 1)
  (princ)
  )
(defun C:CE (/ cen r e el e1 e2 a b c cl d ln ss yn x y)

  (modes '("CMDECHO" "BLIPMODE" "HIGHLIGHT"))
  (setvar "CMDECHO" 0)
  (setvar "BLIPMODE" 0)
  (setq cl (getvar "CLAYER"))
  (if (null $ln) (setq $ln cl))
  (while (null ln)
         (setq ln (getstring (strcat
                               "\nTransfer layer name <"
                               $ln
                               ">: "
                             )
                  )
         )
         (if (= ln "") (setq ln $ln))
         (if (not (tblsearch "LAYER" ln))
             (progn
              (initget "Yes No")
              (setq prmpt (strcat "\nLayer "
                                  (strcase ln t)
                                  " does not exist. Create? <N>: "
                          )
              )
              (setq yn (getkword prmpt))
              (if (= yn "Yes")
                  (command "LAYER" "n" ln "")
                  (setq ln nil)
              )
             )
         )
  )

  (setq $ln ln)
  (prompt "\nSelect trim boundaries: ")
  (setq ss (ssget))
  (setvar "HIGHLIGHT" 0)
  (setq e (entsel "\nSelect entity to conceal "))
  (while e
    (setq e1 (entget (car e)))
    (setq el (entlast))
    (cond  ((= (cdr (assoc 0 e1)) "LINE")
            (xline)
           )
           ((= (cdr (assoc 0 e1)) "ARC")
            (xarc)
           )
           ((= (cdr (assoc 0 e1)) "CIRCLE")
            (xcircle)
           )
           (T (prompt "\nUnsuitable entity selected. "))
    )
    (setq e (entsel "\nSelect entity to conceal "))
  )
  (moder)
  (setvar "highlight" 1)
  (setvar "blipmode" 1)

  (princ)
)
ÿ
