(defun c:gl ()
(setvar "cmdecho" 0)
(prompt "\nPROGRAM BY YELDO VARGHESE...")
(prompt "\nSelect two lines to join:")
(setq a (ssget))
(setq en1 (ssname a 0))
(setq en2 (ssname a 1))
(setq a1 (cdr(assoc 10 (entget en1)))
      b1 (cdr(assoc 11 (entget en1))))
(setq a2 (cdr(assoc 10 (entget en2)))
      b2 (cdr(assoc 11 (entget en2))))
(setq d1 (distance a1 a2)
      d2 (distance a1 b2)
      d3 (distance b1 a2)
      d4 (distance b1 b2))
(if (> d2 d1)
(setq sp a1 ep b2)
(setq sp a1 ep a2))
(if (> d3 (distance sp ep))
(setq sp b1 ep a2))
(if (> d4 (distance sp ep))
(setq sp b1 ep b2))
(setq p (cons 10 sp) p1 (cons 11 ep))
(setq e1 (entget en1))
(setq e1 (subst p (assoc 10 e1) e1) e1 (subst p1 (assoc 11 e1) e1))
(entmod e1)(entdel en2)
(redraw) 
)
