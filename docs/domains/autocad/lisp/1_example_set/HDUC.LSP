;Prepared By :Architect Nguyen Hoai Duc
;**************************************
(setvar "pickbox" 4)
(setvar "aperture" 4)
;ZOOM
(defun c:zp ()  (command "'.zoom" "p"))
(defun c:zw ()  (command "'.zoom" "w"))
(defun c:zz ()  (command "'.zoom" "p"))
(defun c:ze ()  (command "'.zoom" "e"))
(defun c:za ()  (command "'.zoom" "a"))
(defun c:zd ()  (command "'.zoom" "d"))
(defun c:+++ ()  (command "'.zoom" "0.1x"))
(defun c:++ ()  (command "zoom" "0.3x"))
(defun c:+ ()  (command "zoom" "0.5x"))
(defun c:- ()  (command "zoom" "2x"))
(defun c:-- ()  (command "zoom" "3x"))
(defun c:--- ()  (command "zoom" "4x"))
;DIM
(defun c:da () (command "dim" "ali"))
(defun c:du () (command "dim" "up" ))
(defun c:dv () (command "dim" "ver" ))
(defun c:dn () (command "dim" "new" ))
(defun c:dh () (command "dim" "hor" ))
;CHANGE
(defun c:1 () (ssget) (command "change" "p" "" "p" "c" "1" ""))
(defun c:2 () (ssget) (command "change" "p" "" "p" "c" "2" ""))
(defun c:3 () (ssget) (command "change" "p" "" "p" "c" "3" ""))
(defun c:4 () (ssget) (command "change" "p" "" "p" "c" "4" ""))
(defun c:5 () (ssget) (command "change" "p" "" "p" "c" "5" ""))
(defun c:6 () (ssget) (command "change" "p" "" "p" "c" "6" ""))
(defun c:7 () (ssget) (command "change" "p" "" "p" "c" "7" ""))
(defun c:8 () (ssget) (command "change" "p" "" "p" "c" "8" ""))
(defun c:9 () (ssget) (command "change" "p" "" "p" "c" "9" ""))
(defun c:10 () (ssget) (command "change" "p" "" "p" "c" "10" ""))
(defun c:11 () (ssget) (command "change" "p" "" "p" "c" "11" ""))
(defun c:12 () (ssget) (command "change" "p" "" "p" "c" "12" ""))
;UCS
(defun c:cz () (ssget) (command "copy" "p" "" ".xy" "0,0" pause ""))
(defun c:cx () (ssget) (command "copy" "p" "" ".yz" "0,0" pause ""))
(defun c:cy () (ssget) (command "copy" "p" "" ".xz" "0,0" pause ""))
(defun c:mz () (ssget) (command "move" "p" "" ".xy" "0,0" pause ""))
(defun c:mx () (ssget) (command "move" "p" "" ".yz" "0,0" pause ""))
(defun c:my () (ssget) (command "move" "p" "" ".xz" "0,0" pause ""))

(defun c:mb () (command "ucs" "w" "plan" ""))
(defun c:md () (command "ucs" "w" "ucs" "x" "90" "plan" ""))
(defun c:mt () (command "ucs" "w" "ucs" "x" "90" "ucs" "y" "-90" "plan" ""))
(defun c:mh () (command "ucs" "w" "ucs" "x" "90" "ucs" "y" "90" "plan" ""))
(defun c:ms () (command "ucs" "w" "ucs" "x" "90" "ucs" "y" "180" "plan" ""))

(defun c:ui () (command "ucsicon"))
(defun c:uv () (command "ucs" "v"))
(defun c:us () (command "ucs" "s"))
(defun c:ur () (command "ucs" "r"))
(defun c:uw () (command "ucs" "w" "plan" ""))
(defun c:ux () (command "ucs" "x"))
(defun c:uy () (command "ucs" "y"))
(defun c:uz () (command "ucs" "z"))
(defun c:up () (command "ucs" "p"))
(defun c:ue () (command "ucs" "e"))
(defun c:u3 () (command "ucs" "3p" pause pause pause "plan" ""))
(defun c:pc () (command "plan" "c"))
(defun c:vr () (command "view" "r"))
(defun c:vs () (command "view" "s"))
;OSNAP
(defun c:oc () (command "osnap" "cen")(princ))
(defun c:oe () (command "osnap" "end")(princ))
(defun c:oi () (command "osnap" "int")(princ))
(defun c:or () (command "osnap" "per")(princ))
(defun c:on () (command "osnap" "none")(princ))
(defun c:oq () (command "osnap" "qua")(princ))
(defun c:om () (command "osnap" "mid")(princ))
(defun c:ot () (command "osnap" "tan")(princ))
(defun c:os () (command "osnap" "ins")(princ))
;OTHERS
(defun c:arp () (ssget) (command "array" "p" "" "p"))
(defun c:arr () (ssget) (command "array" "p" "" "r"))
(defun c:bf () (command "break" pause "f"))
(defun c:bb () (command "break" pause "f" pause "@"))
(defun c:c2 () (command "circle" "2p"))
(defun c:cm () (ssget) (command "copy" "p" "" "m"))
(defun c:cfd () (command "chamfer" "d"))
(defun c:cf0 () (command "chamfer" "d" "0" ""))
(defun c:dtc () (command "dtext" "j" "c"))
(defun c:dup () (ssget) (command "copy" "p" "" "0,0" "0,0"))
(defun c:ef () (ssget) (command "extend" "p" "" "f"))
(defun c:fr ()(setvar "filletrad" (getdist "\nEnter radius: ")) (command "fillet")(princ))
(defun c:f0 ()(setvar "filletrad" 0) (command "fillet")(princ))
(defun c:in () (command "insert" "" pause "" "" ""))
(defun c:nc () (command "shell" "nc"))
(defun c:pa () (command "pline" pause "a"))
(defun c:pw () (command "pedit" pause "w"))
(defun c:pj () (command "pedit" pause "j"))
(defun c:s () (command "stretch" "c"))
(defun c:sqi () (command "polygon" "4" pause "i"))
(defun c:sqc () (command "polygon" "4" pause "c"))
(defun c:tm0 () (command "tilemode" "0"))
(defun c:tm1 () (command "tilemode" "1"))
(defun c:tri () (command "polygon" "3" pause "i"))
(defun c:trc () (command "polygon" "3" pause "c"))
(defun c:tf () (ssget) (command "trim" "p" "" "f"))
(defun c:xa () (command "xref" "" "~"))
;**************************************
;(defun c:LS (/ ee23 xx23)
;   (setvar "cmdecho" 0)
;   (setq ee23 (car (entsel "\nPick Object on desired layer: ")))
;   (if ee23 (progn
;             (setq ee23 (entget ee23))
;             (setq xx23 (cdr (assoc 8 ee23)))
;             (command "layer" "s" xx23 "")
;          )
;    )
;   (prompt (strcat "\nCurrent layer is now..." xx23))
;   (setvar "cmdecho" 1)
;   (princ)
;)
;**************************************
;(defun c:LF (/ ee23 xx23)
;   (setvar "cmdecho" 0)
;   (setq ee23 (car (entsel "\nPick Object on desired layer: ")))
;   (if ee23 (progn
;             (setq ee23 (entget ee23))
;             (setq xx23 (cdr (assoc 8 ee23)))
;             (command "layer" "f" xx23 "")
;          )
;    )
;   (prompt (strcat  xx23 "\n is now freezed."))
;   (setvar "cmdecho" 1)
;   (princ)
;)
;**************************************
;(defun c:TL (/ lou43)
;   (setvar "cmdecho" 0)
;   (setq lou43 (getstring "\nType layer name: "))
;   (command "undo" "mark")
;   (command "layer" "s" lou43 "")
;   (prompt (strcat "\nCurrent layer is now..." lou43))
;   (setvar "cmdecho" 1)
;   (princ)
;)
;**************************************
(defun c:CLT (/ mpn43 lri44)
    (prompt "\nSelect objects: ")
    (setvar "cmdecho" 0)
    (command "select" "au" pause)
    (setq mpn43 (ssget "p"))
    (setq lri44 (getstring "\nType desired linetype for entiti(es): "))
    (prompt "\nChanging linetype for entiti(es)... stand by.")
    (command "undo" "mark")
    (command "change" mpn43 "" "p" "lt" lri44 "")
    (prompt "\nFinished.")
    (setvar "cmdecho" 1)
    (princ)
)
;**************************************
(defun c:MP (/ list23 lri23 mpn23 lay23 lt23 col23)
  (prompt "\nSelect objects: ")
  (setvar "cmdecho" 0)
  (command "select" "au" pause)
  (setq list23 (ssget "p"))
  (setq lri23 (entsel "\nSelect entity to match: "))
  (prompt "\nChanging entiti(es) properti(es)... stand by.")
  (command "undo" "mark")
  (setq mpn23 (entget (car lri23)))
  (setq lay23 (cdr(assoc 8 mpn23)))
  (setq lt23 (cdr(assoc 6 mpn23)))
  (setq col23 (cdr (assoc 62 mpn23)))
  (if (= lt23 nil) (setq lt23 "bylayer"))
  (if (= lt23 "byblock") (setq lt23 "byblock"))
  (if (= col23 nil) (setq col23 "bylayer"))
  (if (= col23 "byblock") (setq col23 "byblock"))
  (command "change" list23 "" "p" "la" lay23 "c" col23 "lt" lt23 "")
  (prompt "\nFinished.")
  (setvar "cmdecho" 1)
  (princ)
)
;**************************************
(defun c:ML (/ list13 lri13 mpn13 lay13)
  (prompt "\nSelect objects: ")
  (setvar "cmdecho" 0)
  (command "select" "au" pause)
  (setq list13 (ssget "p"))
  (setq lri13 (entsel "\nSelect entity to match: "))
  (command "undo" "mark")
  (setq mpn13 (entget (car lri13)))
  (setq lay13 (cdr (assoc 8 mpn13)))
  (command "change" list13 "" "p" "la" lay13 "")
  (princ)
  (setvar "cmdecho" 1)
)
;**************************************
(defun c:CRT (/ A B C D)
  (setvar "CMDECHO" 0)
  (prompt "\nFor rotated copy")
  (ssget)
  (setq A (getpoint "\nBase point: "))
  (command "ID" A)
  (setq B (getpoint "\nNew point <Return> if same as Base point> "))
  (if (= B nil) (setq B A))
;  (setq D (/ (* (getangle B "\nRotation angle <0>: ") 180.0) pi))
  (command "COPY" "P" "" A A)
  (command "MOVE" "P" "" A B)
  (command "ROTATE" "P" "" B pause)
  (setvar "CMDECHO" 1)
)

;**************************************
