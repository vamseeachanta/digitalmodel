(DEFUN C:GD()
(sETQ PT1(GETPOINT "\nPick first point: "))
(setq pt2(getdist pt1 "\nPick other point: "))
(setq txt(strcat "\nDist = " (rtos pt2 2 2)))
(command "text" "s" "Rs" "m" pause "0" txt)(princ))
(DEFUN C:GD1()
(sETQ PT1(GETPOINT "\nPick first point: "))
(setq pt2(getpoint pt1 "\nPick other point: "))
(setq dp1(list (car pt1) (cadr pt1)))
(setq dp2(list (car pt2) (cadr pt2)))
(setq dis(distance dp1 dp2))
(setq txt(strcat "\nDist =" (rtos dis 2 2)))
(princ txt)
(prompt " Pick point to insert as text")
(command "text" "s" "Rs" "m" pause "0" txt)(princ))
