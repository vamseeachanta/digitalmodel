;This lisp is developed as part of Survey Drawing project, which aims to help people prepare survey drawings easily.
;You may find more such lisps at www.surveydrawing.net and www.esurveying.net


; Program to draw Grid between selected Points with Grid annotation.
(defun c:dgrid()
	(command "_.Undo" "M")
	(Cre_lay "Grid" "8")
	(Cre_lay "GridAnn" "150")
	(setq clay(getvar "Clayer"))
	(command "._Layer" "s" "0" "")
	(setq lp(getpoint "\nLower Left corner :"))
	(setq up(getpoint "\nTop Right corner :"))
	(setq Gr(getint "\nType the Interval :"))
	(initget "Y N")
	(setq snpPnt(getkword "\nSnap Selected Points to Grid Points? Y / <N> :"))
	(if (= snpPnt nil) (setq snpPnt "N"))
	(if (or (= snpPnt "Y") (= snpPnt "y")) (setq snpPnt T) (setq snpPnt nil))
	(if snpPnt
		(progn
			(setq lp(NearestPoint lp Gr))
			(setq up(NearestPoint up Gr))
		)
	)
	(setq xcor1(car lp))
	(setq ycor1(cadr lp))
	(setq xcor2(car up))
	(setq ycor2(cadr up))
	(if (> xcor1 xcor2)
		(progn
			(setq temp xcor2)
			(setq xcor2 xcor1)
			(setq xcor1 temp)
		)
	)
	(if (> ycor1 ycor2)
		(progn
			(setq temp ycor2)
			(setq ycor2 ycor1)
			(setq ycor1 temp)
		)
	)	
	(setq xcor1o xCor1)
	(setq ycor1o yCor1)
	(setq inrxco xcor1)
	(setq inryco ycor1)	
	(if (or (= ycor1 ycor2) (= xcor1 xcor2))
		(progn
			(command "._Line" (list xcor1 ycor1) (list xcor2 ycor2) "")
			(command "._Zoom" "e" "Zoom" ".8x")	 		
			(alert "\nSelection too small to draw grid :")
			(exit)
		)
	)

	(PlaceTextH (list (- xcor1o 2) ycor1o) 0 (strcat "N " (itoa (fix inryco))) "GridAnn" "Mr" 2)
	
	(command "._Line" (list xcor1o ycor1o) (list xcor2 ycor1o) "")
	(command "._Change" (entlast) "" "p" "la" "Grid" "")

	(PlaceTextH (list xcor1o (- ycor1o 2)) (/ pi 2) (strcat "E " (itoa (fix inrxco))) "GridAnn" "ML" 2)
	(command "._Line" (list xcor1o ycor1o) (list xcor1o ycor2) "")
	(command "._Change" (entlast) "" "p" "la" "Grid" "")	
	
	(setq inryco ycor1)
	(while (<= inryco ycor2)
		(if (> inryco yCor1o)
			(progn
				(PlaceTextH (list (- xcor1o 2) inryco) 0 (strcat "N " (itoa (fix inryco))) "GridAnn" "MR" 2)
				(command "._Line" (list xcor1o inryco) (list xcor2 inryco) "")
				(command "._Change" (Entlast) "" "p" "la" "Grid" "")
			)
		)
		(setq inryco(+ inryco Gr))
	)
	(setq inrxco xcor1)
	(while (<= inrxco xcor2)
		(if (> inrxco xCor1o)
			(progn
				(PlaceTextH (list inrxco (- ycor1o 2)) (/ pi 2) (strcat "E " (itoa (fix inrxco))) "GridAnn" "ML" 2)
				(command "._Line" (list inrxco ycor1o) (list inrxco ycor2) "")
				(command "._Change" (Entlast) "" "p" "la" "Grid" "")
			)
		)
		(setq inrxco(+ inrxco Gr))
	)
	(command "._zoom" "e" )
	(princ)
)
(princ "\nType \"DGrid\" at the command Prompt to Create Grid") (princ)

;Function to Find the Nearest Grid Value for given Grid Spacing
(Defun NearestPoint(NP_Point NP_Mod)
	(setq PointX(car NP_Point))
	(setq PointY(cadr NP_Point))
	(setq PointX1(- PointX (rem PointX Np_Mod)))
	(setq PointY1(- PointY (rem PointY Np_Mod)))
	(setq PointX2(+ PointX (- Np_Mod (rem PointX Np_Mod))))
	(setq PointY2(+ PointY (- Np_Mod (rem PointY Np_Mod))))
	(setq PointOne(list PointX1 PointY1))
	(setq PointTwo(list PointX2 PointY1))
	(setq PointThree(list PointX1 PointY2))
	(setq PointFour(list PointX2 PointY2))
	(setq Dist1(distance NP_Point PointOne))
	(setq Dist2(distance NP_Point PointTwo))
	(setq Dist3(distance NP_Point PointThree))
	(setq Dist4(distance NP_Point PointFour))
	(setq Distlist(list Dist1 Dist2 Dist3 Dist4))
	(setq minDist(min Dist1 Dist2 Dist3 Dist4))
	(setq PointNum(- 5 (length (member minDist Distlist))))
	(Cond ((= PointNum 1) (setq NP_Out PointOne))
		((= PointNum 2) (setq Np_Out PointTwo))
		((= PointNum 3) (setq Np_Out PointThree))
		((= PointNum 4) (setq Np_Out PointFour))
	)
	(setq Np_Out Np_Out)
)

;Function to place the text at given point
(Defun PlaceTextH(InIns InAng InText InLay InJust txtHe)
	(setq ang(* (/ InAng pi) 180))
	(if (and (>= ang 90) (<= ang 270)) 
		(setq ang(+ ang 180))
	)
	(setq ang(rtos ang))
	(setq txg (cdr (assoc 40 (tblsearch "STYLE" (GETVAR "TEXTSTYLE")))))
	(if (> txg 0)
		(command "._Text" "j" InJust InIns ang InText)
        (command "._Text" "j" InJust InIns txtHe ang InText)
	)
	(setq laEnt(entlast))
	(command "._Change" laEnt "" "P" "La" InLay "")
)

;Function to Create a Layer with given color
(defun Cre_Lay(lay_layn lay_laycol)
	(if (= (tblsearch "Layer" lay_layn) nil)
		(command "._Layer" "n" lay_layn "c" lay_laycol lay_layn "")
		(command "._Layer" "t" lay_layn "on" lay_layn "c" lay_laycol lay_layn "")
	)
	(princ)
)
