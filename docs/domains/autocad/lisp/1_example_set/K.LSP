(defun c:cor()
(command "osnap" "node")
(setq i (open "c:\\acadwin\\work\\gcor.cor" "w"))
(setq cnt 1)
(while (setq pn (getpoint "\nplease select your point:"))
(setq x (car pn))
(setq y (cadr pn))
(setq z (caddr pn))
(setq x (rtos x 2 3))
(setq y (rtos y 2 3))
(setq z (rtos z 2 3))
(princ cnt i)
(princ "  " i)
(princ x i)
(princ "  " i)
(princ y i)
(princ "   " i)
(princ z i)
(setq cnts (rtos cnt 2 0))
(setq hi (getvar "pdsize"))
(setq npn (polar pn (* hi 2) 0.77))
(setq fpn (polar pn (* hi 5) 0.457))
(command "text" npn 2 0 cnts)
(command "text" fpn 2 50 x)
(command "text" fpn 2 4 y)
(command "text" fpn 2 4 z)
(setq cnt (1+ cnt))
(princ "\n" i)
)
(close i)
)




	(setq hi (getreal"\nText Hight:"))
	(setq spnt (GETINT"\nENTER START PARCEL N#:"))
	(WHILE (SETQ pt (GETPOINT"\nWHERE TO PLACE LABLE ?"))
		(command "text" "m" PT hi 0 SPNT)
		(SETQ SPNT (1+ SPNT))
	)
)
