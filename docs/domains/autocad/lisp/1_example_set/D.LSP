(defun C:d (/ pt1 pt2 datum PT1Y PT2Y PT2L PT2X)
  (COMMAND "-OSNAP" "ENDPOINT")
  (setq pt1 (getpoint "insrtfirestpoint"))
 (setq datum (GETREAL "insetr datum"))
  ;(setq datum 375.00)
  (COMMAND "-OSNAP" "INTersection")
  (setq sc (getreal "scal"))
  (WHILE (setq pt2 (getpoint "insrtsecondpoint"))
    (setq pt1y (cadr pt1))
    (setq pt2y (cadr pt2))
    (setq pt2x (+ (car pt2) 0))
    (SETQ PT2L (RTOS (+ (/ (- PT2Y PT1Y) sc ) DATUM) 2 3))
    (SETQ TX1PT (LIST (+ PT2X 4.0) (+ PT1Y 70)))
    (COMMAND "LAYER" "SET" "DRLEVEL" "")
    (command "OSNAP" "NONE")
    (COMMAND "TEXT" "S" "PRO1 " TX1PT "90" PT2L)
    (COMMAND "-OSNAP" "INTersection")
  )
)
