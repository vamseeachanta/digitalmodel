(defun pre ()
(setq pl (getpoint"\nwhere to place area?"))
	(command "area")
)
(defun fil ()
	(setq ar (getvar "area"))
	(COMMAND "COLOR" BYLAYER)
	(command "LAYER" "THAW" "AREA" "")
	(command "LAYER" "SET" "area" "")
	(setq ar (rtos ar 2 2))
	(command "text" "m" pl 2 0 ar)
)
(defun c:ARE()
(defun *error* (msg)
	(princ "error: ")
	(princ msg)
	(terpri)
)
	(fil)
	(pre)
)
