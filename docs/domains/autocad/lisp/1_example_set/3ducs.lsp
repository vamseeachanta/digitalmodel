(defun c:3ducs (/ om orm p1 p2 p3 px1 py1 pz1 pz3)
  (setq om (getvar "osmode"))
  (setvar "osmode" 0)
  (setq orm (getvar "orthomode"))
  (setvar "orthomode" 1)
  (setq p1 (getpoint "\nSelect First Point in plan: "))
  (if (= p1 nil)(exit))
  (setq p2 (getpoint p1 "\nSelect Second Point in plan: "))
  (if (= p2 nil)(exit))
  (setq px1 (car p1))
  (setq py1 (cadr p1))
  (setq pz1 (cadr (cdr p1)))
  (setq pz3 (+ pz1 10))
  (setq p3 (list px1 py1 pz3))
(command "ucs" "n" "3" p1 p2 p3)
  (setvar "osmode" om)
  (setvar "orthomode" orm)
  (princ)
)
