// this lisp helps to join 2 texts; eg. ch, 0+00 to ch.0+00
(command "style" "rs" "romans" "2.2" "0.8" "" "" "" "")
(defun c:de ()
  (setq toch(entsel "\nPick text to change: "))
  (setq fget1(entget (car toch)))
  (setq ftxt(assoc 1 fget1))
  (setq ftxt1(cdr ftxt))
  (setq sset (ssget))
  (setq count 0)
  (setq slen (sslength sset))
  (command "change" toch "" "" "" "rs" ^c)
  (while (< count slen)
    (setq sget (entget (ssname sset count)))
    (setq asget (assoc 1 sget))
    (setq asget1 (cdr asget))
    (setq len (strlen asget1))
    (setq nstr (strcat ftxt1 " " asget1))
    (command "change" toch "" "" "" "" "" nstr)
    (setq ftxt1 nstr)
    ;(setq sget (subst (cons 1 nstr) asget sget))
    ;(entmod sget)
    (setq count (1+ count))
  )
  (princ)
)
