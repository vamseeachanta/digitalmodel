(defun c:newtp (/ count pt1 num)
	(if (= blk nil) (setq blk "NEWTP"))
	(setq blk1 (strcase (getstring (strcat "\nBlock name to Insert < " blk " >: "))))
	(if (/= blk1 "") (setq blk blk1))
	(setq clay (getvar "CLAYER"))
	(setvar "ATTDIA" 0)
	(setvar "ATTREQ" 1)
	(setq dt (Tblsearch "layer" "NEWTP"))
	(if (= dt nil) (command "layer" "n" "newtp" "s" "newtp" "c" "red" "newtp" ""))
	(setq cl (getvar "clayer"))
	(if (/= cl "NEWTP") (command "layer" "s" "newtp" ""))
	(setq nam (strcat (chr 73) (chr 66) (chr 82) (chr 65) (chr 72) (chr 73) (chr 77)))
	(setq nam1 (strcat "This programme belongs to " nam))
	(while (setq count (getint "\nEnter starting number: "))
		(while (setq pt1 (getpoint "\nPick insertion point: "))
			(grtext -1 nam1)
			(setq num (itoa count) count (1+ count))
			(Command "INSERT" blk pt1 "" "" "" num)
			(grtext 25 nam 25)
		)
	)
	(setvar "CLAYER" clay)
	(princ)
)
