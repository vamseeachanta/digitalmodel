(defun c:chy(/ doc ent hyp new)
  (setq doc (vla-get-activedocument (vlax-get-acad-object)))
  (vla-startundomark doc)
  (while (setq ent (entsel "\nSelect object with hyperlinks : "))
    (setq hyp (vla-get-hyperlinks (vlax-ename->vla-object (car ent))))
    (if (zerop (vla-get-count hyp))
      (princ "\nNo hyperlinks on this object.")
      (while (setq ent (entsel "\nSelect object to paste hyperlinks : "))
	(setq ent (vla-get-hyperlinks (vlax-ename->vla-object (car ent))))
	(vlax-for lin hyp
	  (setq new (vla-add ent "Patrick_35"))
	  (mapcar '(lambda(x) (vlax-put new x (vlax-get lin x))) '(url urldescription urlnamedlocation))
	)
      )
    )
  )
  (vla-endundomark doc)
  (princ)
)
