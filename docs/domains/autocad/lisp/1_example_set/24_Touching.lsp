;This lisp is developed as part of Survey Drawing project, which aims to help people prepare survey drawings easily.
;You may find more such lisps at www.surveydrawing.net and www.esurveying.net



(defun c:TOTX()
	(cre_lay "Touching" "4")
	(command "_.Undo" "M")
	(princ "\n**Note**::Switch on only required Layers to Select Texts.")
	(setq adjSize(* 0.15 (getvar "LTSCALE"))) 
    (setq adjSize2(* 0.17 (getvar "LTSCALE")))
	(princ "\nSelect text entities.")
    (setq selSet(ssget (list (cons 0 "Text"))))
	(if (/= selSet nil)
		(progn
		    (setq selLength(sslength selSet))
		    (setq cntr 0)
			(repeat selLength
				(setq txtEnt(ssname selSet cntr))
				(setq TB(textbox (list (cons -1 txtEnt))))
				(setq SX(nth 1 (assoc 10 (entget txtEnt))))
				(setq SY(nth 2 (assoc 10 (entget txtEnt))))
				(setq ST(list SX SY))
				(setq SR(cdr (assoc 50 (entget txtEnt))))
				(setq X(+ (nth 0 (car TB))(nth 0 (cadr TB))))
				(setq Y(+ (nth 1 (car TB))(nth 1 (cadr TB))))
				(setq C1(polar ST (+ (* pi 1.25) SR) adjSize2))
				(setq C2(polar C1 SR (+ (* adjSize2 1.4) X)))
				(setq C4(polar C1 (+ (* pi 0.5) SR) (+ (* adjSize2 1.4) Y)))
				(setq C3(polar C2 (+ (* pi 0.5) SR) (+ (* adjSize2 1.4) Y)))
				(setq T1(polar ST (+ (* pi 1.25) SR) adjSize))
				(setq T2(polar T1 SR (+ (* adjSize 1.4) X)))
				(setq T4(polar T1 (+ (* pi 0.5) SR) (+ (* adjSize 1.4) Y)))
				(setq T3(polar T2 (+ (* pi 0.5) SR) (+ (* adjSize 1.4) Y)))
				(command "._Zoom" "c" St (* 10 (cdr (assoc 40 (entget txtEnt)))))
				(setq eset(ssget "CP" (list C1 C2 C3 C4)))
				(if (= eset nil)
					(progn (princ "\nProblem with Line :"))
					(progn
						(setq ttl(sslength eset))
						(if (> ttl 1)
							(command "._change" txtEnt "" "p" "layer" "Touching" "")
						)
					)
				)
				(setq cntr(+ cntr 1))
		    )
		)
		(progn
			(princ "\nYou have not selected the texts!")
		)
	)
	(princ)
)
(princ "\nType \"TOTX\" at the command prompt") (princ)

;Function to Create a Layer with given color
(defun Cre_Lay(lay_layn lay_laycol)
	(if (= (tblsearch "Layer" lay_layn) nil)
		(command "._Layer" "n" lay_layn "c" lay_laycol lay_layn "")
		(command "._Layer" "t" lay_layn "on" lay_layn "c" lay_laycol lay_layn "")
	)
	(princ)
)
