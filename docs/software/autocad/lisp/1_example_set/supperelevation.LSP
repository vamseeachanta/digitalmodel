(defun c:sup (/)
(setq st (getpoint "\n click a point to show results) ")
      l(getreal "\n enter length of supperelevation:")
      end(polar st 0 l))
  
  (command "line" st end "")
   (command "zoom" "w" (list(-(car st)10) (+(cadr st)5)) (list(+(car st)(* 2.01(+ 10 l)))(-(cadr st)5)))
 (setq clyr(getvar"clayer"))
(setq sr(getreal "\n enter right cross section slop of the begining(+% or -%):")
      sl(getreal "\n enter left cross section slop of the begining(+% or -%):")
      tr(getreal "\n enter right cross section slop of the end(+% or -%):")
      tl(getreal "\n enter left cross section slop of the end(+% or -%):")
      wr (getreal "\n enter right width: ")
      wl (getreal "\n enter left width: ")
 )
  ;new add
    
    (initget 1)
   (setq pp0 (polar end 0 10))
   (setq dh(-(- 0.2(min(/(* wr sr)100)(/(* wl sl)100)(/(* tr wr)100)(/(* tl wl)100)))))
    ;reach to here
   (setq st0 (list (car pp0)(cadr pp0)))
   (setq stx (polar st0 0 100))
   (setq po1 (list(car pp0)(+(cadr pp0)100)))
   
   (command ".ucs""new" "3p"st0 stx po1);end add 
  
  (setq st(list(-(+ 10 L))0))
  (setq dx (getreal "\n enter enterval between internal sections:"))
  (setq cecolr(getvar"cecolor"))
  (setq osmd(getvar"osmode"))
  (setvar "osmode"0)
  (setq andr(getvar"angdir"))
  (setvar "angdir"1)
  (setq andb(getvar"angbase")) 
  (setvar "angbase"(/ pi 2))
  ( setq aunt(getvar"aunits"))  
  (setvar "aunits"2)
  (setvar "dimaunit"2)
  ( setvar"dimadec"4)

  (command "text"(polar(polar st pi (* 0.12 l))(* 1.5 pi)(* 0.03 l))"1"200"right cross section %:")
  (command "text"(polar(polar st pi (* 0.1 l))(/ pi 2)(* 0.03 l))"1"0"left cross section %:")
  (command "text"(polar st pi 52)"1"100"dh=W*S/100+0.5*[1+cos(200+(200*x/200))]*[(T-s)*w]/100")
  (setq n 0)
  (setq cn(fix(/ l dx)))
  (setq prer(polar(polar st 0 l)(*(- 0.5)pi)wr))
  (setq prel(polar(polar st 0 l)(* 0.5 pi)wl))
  (setq potslst_Le(list(car prel)(cadr prel)(/(* tl wl)100)))
  (setq potslst_Re(list(car prer)(cadr prer)(/(* tr wr)100)))
  (setq potslst_L'())
  (setq potslst_R'())
  (setq lx 0)
  (while
    (< lx l)
    (progn
    (setq lx lx
          ar (/(* sr wr)100)
          br1 (+(cos(+(/(* lx pi)l)pi))1)    
          br2 (/(*(- tr sr)wr)100)
          br (* 0.5 (* br1 br2))
          hr (+ ar br)
	  al (/(* sl wl)100)
          bl1 br1
          bl2 (/(*(- tl sl)wl)100)
          bl (* 0.5(* bl1 bl2))
          hl (+ al bl)
	  )
    
    (setq px(polar st 0 lx))
    (setq pr (polar px (* (- 0.5) pi) wr))
    (setq pl (polar px (* 0.5 pi)wl))
    (setq pots_r(list(car pr)(cadr pr)hr))
    (setq pots_L(list (car pl)(cadr pl)hl))
    
    
    (command "point" (list(car pr)(cadr pr)hr))
    (command "point" (list (car pl)(cadr pl)hl))
    
    (command "point"(list(car prer)(cadr prer)(/(* tr wr)100)))
    (command "point"(list(car prel)(cadr prel)(/(* tl wl)100)))
    (setq potslst_R(append potslst_R pots_r))
    (setq potslst_L(append potslst_L pots_L))
   (setq lx (+ lx dx))
    (setq n(+ 1 n))
	  )
    )
   (setq potslst_r(append potslst_r potslst_re))
   (setq potslst_l(append potslst_l potslst_le))
  (setq c0 0)
  (setq pp0 (list 0 0))
  (setq p0n 1)
  (setq pm0 (polar pp0 pi 6))
  (command "text"(list(car pm0)(+(cadr pm0)0.5)) "1" 100 (rtos dh 2 2))
  (command "layer" "m" "dashes" "")
  (command "layer" "c" "3" "dashes" "")
  (command "color"3)
  (command "line" pp0 pm0 "")
  (command "color"1)
  (command "layer" "m" "text information" "")
  (command "layer" "c" "1" "text information" "")
  (command "text"(list(-(car pp0)7)(-(cadr pp0)2.5))"1"100 "station")
  (command "color"3)
  (command "ucsicon""off")
  (command "color"3)
  (command "text"(list(-(car pp0)11)(-(cadr pp0)16))"1.1"100 "right-level")
  (command "text"(list(-(car pp0)10)(-(cadr pp0)8))"1.1"100 "left-level")
  (setq nx(length potslst_r))
  (setq nr 0)
  (while
    (<= nr (- nx 6))
    (progn
      (setq ps0 (list(nth nr potslst_r)(nth(+ nr 1)potslst_r)))
      (setq gl (nth(+ nr 2)potslst_r))
    (command "layer" "m" "الارقام الصفراء" "")
  (command "layer" "c" "2" "الارقام الصفراء" "")
  (command "color" "bylayer") 
  (command "text"(list(car ps0)(+(cadr ps0)0.5)) "1"100 (rtos p0n 2 0))
(setq e0 (polar pp0 (/ pi -2)12))
  (setq e1 (polar pp0 (/ pi -2)6))    
 (command "layer" "m" "dashes" "")
  (command "layer" "c" "2" "dashes" "")
  (command "color" "bylayer") 
  (command "line" pp0 e1 "")
  (command "layer" "m" "text information" "")
  (command "layer" "c" "3" "text information" "")
  (command "color""3")
  (command "text"(list(car pp0)(+(cadr pp0)0.5)) "1.1"100 (rtos p0n 2 0))
  (command "text"e0 "1"200 (rtos gl 2 3))
  (setq gx0 (list (car pp0)(+(cadr pp0)(* 10(- gl dh)))))
  (command "layer" "m" "dashes" "")
  (command "layer" "c" "2" "dashes" "")
  (command "color"15)
  (command "line"pp0 gx0 "")
  (command "layer" "m" "text information" "")
  (command "layer" "c" "1" "text information" "")
  (command "color""bylayer")  
  (command "text"pp0 "1" 200  (rtos c0 2 3))
  (command "color"4)
  (command "layer" "m" "G-point" "")
  (command "layer" "c" "1" "G-point" "")
  (command "color"3)
  (command "point" gx0);end right level
   (setq ps0 (list(nth nr potslst_l)(nth(+ nr 1)potslst_l)))
      (setq gl (nth(+ nr 2)potslst_l))
    (command "layer" "m" "الارقام الصفراء" "")
  (command "layer" "c" "2" "الارقام الصفراء" "")
  (command "color" "bylayer") 
  (command "text"(list(car ps0)(+(cadr ps0)0.5)) "1"100 (rtos p0n 2 0))
  (setq e0 (polar pp0 (/ pi -2)6))
  (command"color"3) 
  (command "text"e0 "1"200 (rtos gl 2 3))
  (setq gx0 (list (car pp0)(+(cadr pp0)(* 10(- gl dh)))))
  (command "color"4)
  (command "layer" "m" "G-point" "")
  (command "layer" "c" "1" "G-point" "")
  (command "color"3)
  (command "point" gx0);end left levels   
      (setq p0n(+ 1 p0n))
      (setq c0(+ c0 dx))
  (setq pp0(list(+(car pp0)dx)0))
  (setq nr(+ 3 nr))
	)
    )
  ;start for end point
  (setq ps0 (list(nth(- nx 3) potslst_r)(nth(- nx 2)potslst_r)))
  (setq gl (nth(- nx 1)potslst_r))
  (setq pp0(list L 0))
  (setq c0 L)
  (setq p0n p0n)
  (command "layer" "m" "الارقام الصفراء" "")
  (command "layer" "c" "2" "الارقام الصفراء" "")
  (command "color" "bylayer") 
  (command "text"(list(car ps0)(+(cadr ps0)0.5)) "1"100 (rtos p0n 2 0))
  (setq e0 (polar pp0 (/ pi -2) 12))
  (setq e1 (polar pp0 (/ pi -2)6))
  (command "layer" "m" "dashes" "")
  (command "layer" "c" "2" "dashes" "")
  (command "color" "bylayer") 
  (command "line" pp0 e1 "")
  (command "layer" "m" "text information" "")
  (command "layer" "c" "3" "text information" "")
  (command "color""3")
  (command "text"(list(car pp0)(+(cadr pp0)0.5)) "1.1"100 (rtos p0n 2 0))
  (command "text"e0 "1"200 (rtos gl 2 3))
  (setq gx0 (list (car pp0)(+(cadr pp0)(* 10(- gl dh)))))
  (command "layer" "m" "dashes" "")
  (command "layer" "c" "2" "dashes" "")
  (command "color"15)
  (command "line"pp0 gx0 "")
  (command"color"4)
  (command "line"(list 0 (* dh(- 10 20)))(list l(* dh(- 10 20)))"")
  (command"text"(list l(* dh(- 10 20)))"1"100"zero axis")
  (command "layer" "m" "text information" "")
  (command "layer" "c" "1" "text information" "")
  (command "color""bylayer")  
  (command "text"pp0 "1" 200  (rtos c0 2 3))
  (command "color"4)
  (command "layer" "m" "G-point" "")
  (command "layer" "c" "1" "G-point" "")
  (command "color"3)
  (command "point" gx0)
  ;start left end level
   (setq ps0 (list(nth(- nx 3) potslst_l)(nth(- nx 2)potslst_l)))
  (setq gl (nth(- nx 1)potslst_l))
  (setq pp0(list L 0))
  (setq c0 L)
  (setq p0n p0n)
  (command "layer" "m" "الارقام الصفراء" "")
  (command "layer" "c" "2" "الارقام الصفراء" "")
  (command "color" "bylayer") 
  (command "text"(list(car ps0)(+(cadr ps0)0.5)) "1"100 (rtos p0n 2 0))


 (setq e0 (polar pp0 (/ pi -2)6))
(command "layer" "m" "text information" "")
  (command "layer" "c" "1" "text information" "")
  (command "color""bylayer")
  

 (command "color"3) 
(command "text"e0 "1"200 (rtos gl 2 3))
(setq gx0 (list (car pp0)(+(cadr pp0)(* 10(- gl dh)))))
  (command "layer" "m" "G-point" "")
  (command "layer" "c" "1" "G-point" "")
  (command "color"3)
  (command "point" gx0)

(setq potssec_r'())
(setq potssec_l'())  
(setq n2 0)
  (while(< n2 nx)
    (setq potssec_r(append potssec_r(list(+(nth n2 potslst_r)(+ l 10))
					 (* 10(-(nth(+ n2 2)potslst_r)dh)))))
    (setq potssec_l(append potssec_l(list(+(nth n2 potslst_l)(+ l 10))
					 (* 10(-(nth(+ n2 2)potslst_l)dh)))))
     (setq n2(+ n2 3))
    )
  (setq nsec(length potssec_r))
  (setq nsec1 0)
  (command".pline"(list 0(nth 1 potssec_l)))
(while(< nsec1 nsec)
  (setq x2(nth(+ nsec1 2)potssec_l))
  (setq y2(nth(+ nsec1 3)potssec_l))
  (setq nsec1 (+ nsec1 2))
  (command (list x2 y2))
  )
  (command"")
  (setq pl1(entlast))
  (command".pedit"pl1 "f" "")
  (terpri)
  (setq nsec1 0)
(command".pline"(list 0(nth 1 potssec_r)))
(while(< nsec1 nsec)
  (setq x2(nth(+ nsec1 2)potssec_r))
  (setq y2(nth(+ nsec1 3)potssec_r))
  (setq nsec1 (+ nsec1 2))
  (command (list x2 y2))
  )
  (command"")
  (setq pl2(entlast))
  (command".pedit"pl2 "f" "")
  (command"text"st "0.75"0(strcat(rtos sl 2 2)"%"))
  (command"text"(polar st 0 l) "0.75"0(strcat(rtos tl 2 2)"%"))
  (command"text"st "0.75"200(strcat(rtos sr 2 2)"%"))
  (command"text"(polar st 0 l)"0.75"200(strcat(rtos tr 2 2)"%"))
  (setvar"clayer"clyr)
  (setvar"cecolor"cecolr)
  (setvar"angbase"andb)
  (setvar "angdir"andr)
  (setvar"aunits"aunt)
  )
