(defun  Ve_thep ()
  (setq SH so_hieu_thep)
  (setq a coroi)
  (setq Loai_thep (menu))
  (setq x (car vi_tri))
  (setq y (cadr vi_tri))
  (setq y (- y 8.8))
  (cond
    ((= Loai_thep "Luoi")
      (setq DD (getreal "Moc thep <60>:"))
      (if (= DD nil) (setq DD 60))
      (initget (+ 1 2 4))
      (setq DG (getreal "Chieu dai:"))
      (setq DK (getreal "Duong kinh <8>:"))
      (if (= DK nil) (setq DK 8))
      (initget (+ 1 2 4))
      (setq SL (getint "So luong:"))
      (setq CD (+ DG (* 2 DD)))
      (setq TCD (* SL CD))
      (setq TCD (/ TCD 1000))
      (setq tkl 0)
      (cond
         ((= DK 6)  (setq TKL (* TCD 0.222)))
         ((= DK 8)  (setq TKL (* TCD 0.395)))
         ((= DK 10) (setq TKL (* TCD 0.617)))
         ((= DK 12) (setq TKL (* TCD 0.888)))
         ((= DK 14) (setq TKL (* TCD 1.208)))
         ((= DK 16) (setq TKL (* TCD 1.578)))
         ((= DK 18) (setq TKL (* TCD 1.998)))
         ((= DK 20) (setq TKL (* TCD 2.466)))
         ((= DK 22) (setq TKL (* TCD 2.984)))
         ((= DK 25) (setq TKL (* TCD 3.88)))
      )
      (setq y (- y (* (- a 1) 8)))
      (setq DD (rtos DD 2 0))
      (setq DG (rtos DG 2 0))
      (setq DK (rtos DK 2 0))
      (setq CD (rtos CD 2 0))
      (setq TCD (rtos TCD 2 2))
      (setq TKL (rtos TKL 2 2))
      (command "insert" Loai_thep (list x y) "1" "1" "0" SH DG DD DD CD DK SL TKL TCD)
    )
    ((= Loai_thep "Am")
      (setq DD (getreal "Mau thep <70>:"))
      (if (= DD nil) (setq DD 70))
      (initget (+ 1 2 4))
      (setq DG (getreal "Chieu dai:"))
      (setq DK (getreal "Duong kinh <8>:"))
      (if (= DK nil) (setq DK 8))
      (initget (+ 1 2 4))
      (setq SL (getint "So luong:"))
      (setq CD (+ DG (* 2 DD)))
      (setq TCD (* SL CD))
      (setq TCD (/ TCD 1000))
      (setq tkl 0)
      (cond
         ((= DK 6)  (setq TKL (* TCD 0.22)))
         ((= DK 8)  (setq TKL (* TCD 0.40)))
         ((= DK 10) (setq TKL (* TCD 0.62)))
         ((= DK 12) (setq TKL (* TCD 0.89)))
         ((= DK 14) (setq TKL (* TCD 1.22)))
         ((= DK 16) (setq TKL (* TCD 1.59)))
         ((= DK 18) (setq TKL (* TCD 2.01)))
         ((= DK 20) (setq TKL (* TCD 2.48)))
         ((= DK 22) (setq TKL (* TCD 3.00)))
         ((= DK 25) (setq TKL (* TCD 3.88)))
      )
      (setq y (- y (* (- a 1) 8)))
      (setq DD (rtos DD 2 0))
      (setq DG (rtos DG 2 0))
      (setq DK (rtos DK 2 0))
      (setq CD (rtos CD 2 0))
      (setq TCD (rtos TCD 2 2))
      (setq TKL (rtos TKL 2 2))
     (command "insert" Loai_thep (list x y) "1" "1" "0" DD SH DD DG CD DK SL TKL TCD)
    )
    ((= Loai_thep "Gap")
      (setq DD (getreal "Mau thep <250>:")) 
      (if (= DD nil) (setq DD 250))
      (initget (+ 1 2 4))
      (setq DG (getreal "Chieu dai:"))
      (setq DK (getreal "Duong kinh <8>:"))
      (if (= DK nil) (setq DK 8))
      (initget (+ 1 2 4))
      (setq SL (getint "So luong:"))
      (setq CD (+ DG DD))
      (setq TCD (* SL CD))
      (setq TCD (/ TCD 1000))
      (setq tkl 0)
      (cond
         ((= DK 6)  (setq TKL (* TCD 0.22)))
         ((= DK 8)  (setq TKL (* TCD 0.40)))
         ((= DK 10) (setq TKL (* TCD 0.62)))
         ((= DK 12) (setq TKL (* TCD 0.89)))
         ((= DK 14) (setq TKL (* TCD 1.22)))
         ((= DK 16) (setq TKL (* TCD 1.59)))
         ((= DK 18) (setq TKL (* TCD 2.01)))
         ((= DK 20) (setq TKL (* TCD 2.48)))
         ((= DK 22) (setq TKL (* TCD 3.00)))
         ((= DK 25) (setq TKL (* TCD 3.88)))
      )
      (setq y (- y (* (- a 1) 8)))
      (setq DD (rtos DD 2 0))
      (setq DG (rtos DG 2 0))
      (setq DK (rtos DK 2 0))
      (setq CD (rtos CD 2 0))
      (setq TCD (rtos TCD 2 2))
      (setq TKL (rtos TKL 2 2))
        (command "insert" Loai_thep (list x y) "1" "1" "0" TCD TKL SL DK CD DG DD SH)
    )
    ((= Loai_thep "Dai")
      (setq DD (getreal "Moc thep <60>:"))
      (if (= DD nil) (setq DD 60))
      (initget (+ 1 2 4))
      (setq CC (getreal "Chieu cao:"))
      (initget (+ 1 2 4))
      (setq BR (getreal "Be rong:"))
      (initget (+ 1 2 4))
      (setq DK (getreal "Duong kinh <6>:"))
      (if (= DK nil) (setq DK 6))
      (initget (+ 1 2 4))
      (setq SL (getint "So luong:"))
      (setq CD (+ (+ (* 2 CC) (* 2 DD)) (* 2 BR)))
      (setq TCD (* SL CD))
      (setq TCD (/ TCD 1000))
      (setq tkl 0)
      (cond
         ((= DK 6)  (setq TKL (* TCD 0.22)))
         ((= DK 8)  (setq TKL (* TCD 0.40)))
         ((= DK 10) (setq TKL (* TCD 0.62)))
         ((= DK 12) (setq TKL (* TCD 0.89)))
         ((= DK 14) (setq TKL (* TCD 1.22)))
         ((= DK 16) (setq TKL (* TCD 1.59)))
         ((= DK 18) (setq TKL (* TCD 2.01)))
         ((= DK 20) (setq TKL (* TCD 2.48)))
         ((= DK 22) (setq TKL (* TCD 3.00)))
         ((= DK 25) (setq TKL (* TCD 3.88)))
      )
      (setq y (- y (* (- a 1) 8)))
      (setq DD (rtos DD 2 0))
      (setq CC (rtos CC 2 0))
      (setq BR (rtos BR 2 0))
      (setq DK (rtos DK 2 0))
      (setq CD (rtos CD 2 0))
      (setq TCD (rtos TCD 2 2))
      (setq TKL (rtos TKL 2 2))
      (command "insert" Loai_thep (list x y) "1" "1" "0" SH CC BR DD DK CD Sl TKL TCD)
    )
    ((= Loai_thep "Thang")
      (setq DG (getreal "Chieu dai:"))
      (setq DK (getreal "Duong kinh <10>:"))
      (if (= DK nil) (setq DK 10))
      (initget (+ 1 2 4))
      (setq SL (getint "So luong:"))
      (setq CD DG)
      (setq TCD (* SL CD))
      (setq TCD (/ TCD 1000))
      (setq TKL 0)
      (cond
         ((= DK 6)  (setq TKL (* TCD 0.22)))
         ((= DK 8)  (setq TKL (* TCD 0.40)))
         ((= DK 10) (setq TKL (* TCD 0.62)))
         ((= DK 12) (setq TKL (* TCD 0.89)))
         ((= DK 14) (setq TKL (* TCD 1.21)))
         ((= DK 16) (setq TKL (* TCD 1.58)))
         ((= DK 18) (setq TKL (* TCD 2.00)))
         ((= DK 20) (setq TKL (* TCD 2.47)))
         ((= DK 22) (setq TKL (* TCD 2.99)))
         ((= DK 25) (setq TKL (* TCD 3.85)))
         ((= DK 28) (setq TKL (* TCD 4.83)))
         ((= DK 32) (setq TKL (* TCD 6.32)))
      )
      (setq y (- y (* (- a 1) 8)))
      (setq DG (rtos DG 2 0))
      (setq DK (rtos DK 2 0))
      (setq CD (rtos CD 2 0))
      (setq TCD (rtos TCD 2 2))
      (setq TKL (rtos TKL 2 2))
      (command "insert" Loai_thep (list x y) "1" "1" "0" SH DG DK CD SL TKL TCD)
    )
    ((= Loai_thep "Chuaco")
      (setq CD (getreal "Chieu dai:"))
      (setq DK (getreal "Duong kinh <6>:"))
      (if (= DK nil) (setq DK 6))
      (initget (+ 1 2 4))
      (setq SL (getint "So luong:"))
      (setq TCD (* SL CD))
      (setq TCD (/ TCD 1000))
      (setq TKL 0)
      (cond
         ((= DK 6)  (setq TKL (* TCD 0.22)))
         ((= DK 8)  (setq TKL (* TCD 0.40)))
         ((= DK 10) (setq TKL (* TCD 0.62)))
         ((= DK 12) (setq TKL (* TCD 0.89)))
         ((= DK 14) (setq TKL (* TCD 1.22)))
         ((= DK 16) (setq TKL (* TCD 1.59)))
         ((= DK 18) (setq TKL (* TCD 2.01)))
         ((= DK 20) (setq TKL (* TCD 2.48)))
         ((= DK 22) (setq TKL (* TCD 3.00)))
         ((= DK 25) (setq TKL (* TCD 3.88)))
      )
      (setq y (- y (* (- a 1) 8)))
      (setq DK (rtos DK 2 0))
      (setq CD (rtos CD 2 0))
      (setq TCD (rtos TCD 2 2))
      (setq TKL (rtos TKL 2 2))
      (command "insert" Loai_thep (list x y) "1" "1" "0" SH DK CD SL TKL TCD)
    )
  )
)

( defun menu()
    (initget "Luoi Am Gap Dai Thang Chuaco")
    (setq opt (getkword "\nThang/Luoi/Am/Gap/Dai/Chuaco/<Thang>: ")) ; Lua chon loai thep
    (if (= opt nil) (setq opt "Thang"))
    (setq opt opt)
)

(defun c:tk()
  (setq coroi 0)
  (setq vi_tri (getpoint "Vi tri bang vat lieu"))
  (command "insert" "dau" vi_tri "1" "1" "0")
  (while (/= (setq Ten_KC (getstring T "\nTen K.cau <Go Enter de thoat khoi BTK>: ")) "")   ; Nhap ten ket cau
    (setq so_luong_KC (getstring "\nSo luong K.cau: ")) ; Nhap so luong ket cau
    (setq so_hieu_thep 0)
    (initget (+ 1 2 4))
    (setq so_loai_thep (getint "\nSo loai thep: "))
    (repeat so_loai_thep
       (setq coroi (1+ coroi))
       (setq so_hieu_thep (1+ so_hieu_thep))
       (Ve_Thep)
    )                                                          ; End repeat
    (setq tdx (car vi_tri))
    (setq tdy (cadr vi_tri))
    (setq tdy (- tdy 8.8))
    (setq tdy (- tdy (* coroi 8)))
    (Command "LINE" (list tdx tdy) "@123.1155,0" "")
    (Command "Pan" (list tdx tdy) (getvar "VIEWCTR"))
    (Command "Change" "Last" "" "P" "C" "Cyan" "")
    (setq tdx (+ tdx 7.5))
    (setq tdy (+ tdy (/ (* so_loai_thep 8) 2)))
    (Command "text" "S" "bangtk" "j" "bc" (list tdx tdy) "3.5" "90" (strcase Ten_KC))
    (Command "Pan" (list tdx tdy) (getvar "VIEWCTR"))
    (Command "Change" "Last" "" "P" "C" "White" "")
    (if ( /= So_luong_kc "")
     (progn
        (Command "text" "" (strcat "(" So_luong_KC " CAI)" ))
        (Command "Change" "Last" "" "" "" "" "2.5" "" "")
        (Command "Change" "Last" "" "P" "C" "White" "")
        (Command "Move" "Last" "" (list 0 0) "@-1,0")
     )
    ) 
  )                                                             ; End While
)                                                               ; End BTK
(setvar "cmdecho" 0)
(command "insert" "bangtk" (list 0 0) "1" "1" "0")
(princ "\nLenh tu dong lap bang thong ke. BTK")
(princ "\nOK...")
(princ)
