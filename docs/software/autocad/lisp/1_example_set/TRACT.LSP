(defun C:TT ()
(defun *error* (msg)
	(princ "error: ")
	(princ msg)
	(terpri)
)
  (initget "Straight Trelateration Arcs")
  (setq t1 (getkword
     "\n>>Straight Computation/Trelateration/Arcs Drawing: "))
  (setq opt
     (cond
        ((eq t1 "Straight")      1)
        ((eq t1 "Trelateration")      2)
        ((eq t1 "Arcs")      3)))
  (initget 1)
	(command "LAYER" "THAW" "TRANS" "")
	(command "LAYER" "SET" "TRANS" "c" 1 "" "")
	(setvar "cmdecho" 0)
	(command "osnap" "node"
		"color" "bylayer"
	)
	(setvar "pdmode" 32)
	(setvar "pdsize" 3)
(if (= opt 1)
	(progn
		(while (setq i (open "test.sad" "w"))
			(command "osnap" "node")
			(setq sp (getpoint "\nSELECT FIRST POINT:")
				ep (getpoint "\nSELECT SECOND POINT:")
				num (getint "\nNUMBER OF PIECES IN TO WHICH LINE WILL BE BROKEN:")
				ang (angle sp ep)
				dcom (distance sp ep)
				num1 (1+ num)
			)
			(command "osnap" "none")
			(setq test 1
				dchk 0
			)
			(princ "(" i)
	(while (< test num1)
		(progn
			(setq dis (getreal "\nENTER DISTANCE:")
				dchk (+ dchk dis)
			)
			(princ "(" i)
			(princ test i)
			(princ " " i)
			(princ dis i)
			(princ ")" i)
			(setq test (1+ test))
	)
)
			(princ ")" i)
(close i)
			(setq def (- dchk dcom))
			(PROMPT "\nERROR IN DISTNACES *** ")
			(setq def (rtos def 2 2))
			(prompt def)
			(prompt " ***")
			(initget 1 "YES NO")
			(setq ans (getkword "\nDO YOU WISH TO CONTINUE (YES/NO):"))
(if (= ans "YES")
	(progn
		(setq i (open "test.sad" "r")
			al (read-line i)
			al (read al)
		)
(close i)
		(setq test 1)
		(while (< test num1)
			(progn
				(setq obd (cadr (assoc test al))
					pt (polar sp ang obd)
				)
				(command "point" pt
					"line" sp pt
					""
				)
			(setq sp pt)
			(setq test (1+ test))
	)
)
	)
)
	)
)
)
(if (= opt 2)
	(progn
		(setq sp (getpoint "\nSELECT FIRST POINT:")
			dh1 (getreal "\nENTER DISTANCE:")
			ep (getpoint "\nSELECT SECOND POINT:")
			dh2 (getreal "\nENTER DISTANCE:")
			dhc (distance sp ep)
		)
(if (> (+ dh1 dh2) dhc)
	(progn
		(setq vc (angle sp ep)
			pan (/ (- (+ (* dh1 dh1) (* dhc dhc)) (* dh2 dh2)) (* dh1 dhc 2))
			lat (sqrt (- 1 (* pan pan)))
			an (atan (/ lat pan))
			vf (+ vc an)
			ptc (polar sp vf dh1)
		)
		(command "point" ptc)
	)
)
(if (<= (+ dh1 dh2) dhc) (prompt "\nCOMPUTATION IS IMPOSSIBLE"))
	)
)
(if (= opt 3)
	(progn
		 (initget "Hight Three")
		  (setq t1 (getkword
		     "\n>>Hight Of Arc/Three Points: "))
		  (setq sel
		     (cond
		        ((eq t1 "Hight")      1)
		        ((eq t1 "Three")      2)))
			  (initget 1)
	)
)
(if (= sel 1)
	(progn
		(command "osnap" "node")
		(while (setq sp (getpoint "\nSELECT FIRST POINT:")
			ep (getpoint "\nSELECT SECOND POINT:")
			arh (getreal "\nARC HIGHT:")
			dh (distance sp ep)
			vc (angle sp ep)
			dd (/ dh 2)
			radi (/ (+ (* arh arh) (* dd dd)) (* arh 2))
			dhr (- radi arh)
			pan (/ (- (+ (* dd dd) (* radi radi)) (* dhr dhr)) (* dd radi 2))
			lat (sqrt (- 1 (* pan pan)))
			an (atan (/ lat pan))
			vf (- vc an)
			ptc (polar sp vf radi)
			)
			(command "osnap" "none")
			(command "arc" "c" ptc ep sp)
			(command "osnap" "node")
		)
	)
)
(if (= sel 2)
	(progn
			(setq test 0)
		(while (< test 0.10)
			(command "osnap" "node")
			(setq pt1 (getpoint"\nSELECT FIRST POINT:"))
			(setq pt2 (getpoint"\nSELECT SECOND POINT:"))
			(setq pt3 (getpoint"\nSELECT THIRD POINT:"))
			(setq d1 (distance pt1 pt2))
			(setq d2 (distance pt1 pt3))
			(setq d3 (distance pt3 pt2))
			(setq dd1 (/ d1 2))
			(setq d4 (sqrt (- (* d3 d3) (* dd1 dd1))))
			(setq ap1 (atan (/ d4 dd1)))
			(setq ap2 (atan (/ dd1 d4)))
			(setq aut (cos ap2))
			(setq rad (/ dd1 aut))
			(setq bea (angle pt1 pt2))
			(setq ang (- bea ap2))
			(setq ptc (polar pt1 ang rad))
			(setq test (- d2 d3))
			(setq test (abs test))
			(if (< test 0.10)
				(progn
				(command "osnap" "none")
				(command "arc" "c" ptc pt2 pt1)
				(setq d5 (sqrt (- (* rad rad) (* dd1 dd1))))
				(setq h (- rad d5))
				(setq h (rtos h 2 2))
				(setq d1 (rtos d1 2 2))
				(princ "\nARC HIGHT IS: ")
				(princ h)
				(princ "  COORD IS: ")
				(princ d1)
				)
			)
		)
			 (princ "\nWrong distances...check transaction")
	)
)
                         (princ)
		(command "osnap" "none")
		(prin1)
)
