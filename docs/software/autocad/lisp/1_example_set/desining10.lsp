;;;;;;هذا البرنامج لرسم الخط التصميمي;;;;;;;;;;
(defun c:des ()
              (command "osnap" "END" "INT")
                   ;;;إعمل طبقة للخط التصميمي;;        
            (command "layer" "m" "pg" "c" "3" "" "")            
         ;;;;;;;;إسأل المستخدم عن نقطة خط القاعدة;;;;;;;;;;;
            (while (= originy nil) 
                             (setq datumpoint (getpoint "\nPlease Enter The Datum Elevation <>:"))
                             (setq originy (cadr datumpoint))
            )
         ;;;;;;;;إسأل المستخدم عن المحطات ;;;;;;;;;;;
            (while (= station nil) 
                             (setq station (getdist "\nPlease Enter The Stationing Distance<>:")))
     ;;; إسأل المستخدم عن أول نقطة على الخط التصميم وثاني نقطة  ;;;;
           (setq pg1 (getpoint "\nPlease Enter The First  P.V.I.POINT <>:"))    
           (setq pg2 (getpoint "\nPlease Enter The Second P.V.I.POINT <>:"))
      ;;;;;;;;;حساب المسافات والميول;;;;;;;;;; 
            (setq xx1 (car pg1))    
            (setq xy1 (/ (cadr pg1)10))
            (setq xx2 (car pg2))    
            (setq xy2 (/ (cadr pg2)10))
      :::إبدأ في إدخال نقاط المنحنى الرأسي التالية ;;;;;;;;;
      (while (setq pg3 (getPOINT "\nPlease Enter The Next  P.V.I.POINT <>:"))
             (setq lc (getdist "\nPlease Enter The Length Of Vertical Curve <>:"))            
             (setq xx3 (car pg3))    
             (setq xy3 (/ (cadr pg3)10))
             (setq g1 (/(- xy2 xy1) (- xx2 xx1)))
             (setq g2 (/(- xy3 xy2) (- xx3 xx2)))
       ;;;;; إحسب عناصر المنحنى الرأسي ;;;;;;;;;;;;;;;
             (setq s1 (- xx2 (/ lc 2)))  ;محطة بداية المنحني 
             (setq s2 (+ xx2 (/ lc 2)))  ;محطة نهاية المنحني
             (setq e (* (/ (- g1 g2) 8) lc))
       ;;;;;;;;;احسب المناسيب وارسم خط واكتبها  ;;;;;;
                  (setq s xx1)
   ;;;;;;; ;;;;;;رسم الخط التميمي بين أول نقطة وبداية أول منحنى;;;;;;;;;;;
                    (command "osnap" "off" )
         (While (<= s s1) 
                    (setq y (+ (* (- s xx1) g1) xy1))
                    (setq pt (list s (* y 10))) 
              ;;;;;;;رسم خط التصميم ;;;;;;;;;;;;;;;;;
                    (command "layer" "set" "pg" "")
                    (command "line" pg1 pt "")    
                    (setq textx (car pt))    
                    (setq texty originy) 
                    (setq ptxt (list textx texty)) 
                    (setq pviy (+ originy 250)) 
		    (setq pvi (list (- xx2 35) pviy)) 
		    (setq pgi (list ( - xx2 (/ lc 2)) (- pviy 40)))
                    (setq ptxt (polar ptxt (/(* -13 pi) 24 ) 35.0))
               ;;;;;;;كتابة المحطات ومنسوب الخط التصميمي  ;;;;;;;;;;;;;;;;;    
                   ; (command "layer" "set" "txt" "")
                    (command "text" "j" "ml" ptxt 5.0 90.0 (rtos y 2 3)) 
                    (setq s (+ s station))
                    (setq pg1 pt)    
              )
    :::::::::::::رسم نقاط المنحنى ;;;;;;;;;;;;;;;;;;;;;;;;;;;;;;
                      (setq as (/ station 2))
                      (setq s (- s as))
              (While (<= s s2 ) 
                      (setq f xy1)
                      (setq u (* (- s xx1) g1))
                      (setq f (+ u xy1))
                      (setq d (* (- s s1) (- s s1)))
		      (setq d (* d e 4 ))
                      (setq d (/ d lc lc))
                      (setq y (- f d))       
                      (setq pt (list s (* y 10)))
           ;;;;;;;رسم خط التصميم في المنحنى ;;;;;;;;;;;;;;;;;
                      (command "layer" "set" "pg" "")
                      (command "pline" pg1 pt "")    
                      (setq textx (car pt))    
                      (setq ptxt (list textx texty)) 
                      (setq ptxt (polar ptxt (/(* -13 pi)24) 35.0))
                ;;;;;;;كتابة المحطات ومنسوب الخط التصميمي  ;;;;;;;;;;;;;;;;;    
                      (command "text" "j" "ml" ptxt 5.0 90.0 (rtos y 2 3)) 
                      (setq s (+ s  as))
                      (setq pg1 pt)    
              )
              ;;;;;كتابة بيانات نقطة التحول;;;;;;;;; 
                   (setq pcircle (list xx2 (+ originy 200)))
                  (command "circle" pcircle 5 )
                  ;(command "POINT" pcircle )
            (setq st xx2 )
            (setq inst (/ st 1000))
            (setq inst (fix inst))
            (setq frst (- st (* inst 1000)))
            (setq frst (RTOS frst 2 0))
            (setq le (strlen frst))            
            (if (< le 3) (setq frst (strcat "0" frst)))
            (setq ST (strcat (rtos inst 2 0) "+"  frst ))                   
                   (setq stat  "STAT   : ")                     
                   (setq stat (strcat STAT st))
                   (setq ELEV (strcat "ELEV..  : "  (RTOS XY2 2 3)))
                   (setq LENGTH (strcat "LENGTH : " (RTOS LC 2 3)))
                   (setq EE (strcat "E      : "  (RTOS E 2 3)))
		   (command "text" "j" "ml" pvi 7.5 0.0 "   P.V.I " )
		   (command "text" "J" "ML" (POLAR pvi (/(* -1 PI)2) 8.5) 5.0 0.0 STAT )
		   (command "text" "J" "ML" (POLAR pvi (/(* -1 PI)2) 16) 5.0 0.0 ELEV )
		   (command "text" "J" "ML" (POLAR pvi (/(* -1 PI)2) 23.5) 5.0 0.0 LENGTH )
		   (command "text" "J" "ML" (POLAR pvi (/(* -1 PI)2) 31) 5.0 0.0 EE )
		   (command "REDRAW")  
      ;;;;;;;;;;;;;;;;;;;;;;;;إكتب الجريد السابق;;;;;;;;;;;;;;;;;;;;		  
                   (command "text" "J" "Mr" (POLAR pgi (* +1 PI) 30) 5.0 0.0 (strcat "G = "  (RTOS G1 2 5)) )
	;;;;;;;تغير القيم لحساب ورسم النحنى التالي;;;;;;;;;;;
        (setq xx1 (+ xx2 (/ lc 2)))
        (setq xy1  y)
        (setq pg1 (list xx1 (* xy1 10)))
        (setq xx2 xx3)
        (setq xy2 xy3)
                 (command "osnap" "END" "INT" )
     )
           (command "osnap" "off" )   
                   (setq s xx1)
                    (setq g1 (/(- xy2 xy1) (- xx2 xx1)))      
       (While (<= s xx2) 
                    (setq y (+ (* (- s xx1) g1) xy1))
                    (setq pt (list s (* y 10))) 
              ;;;;;;;رسم خط التصميم إلى نقطة النهاية;;;;;;;;;;;;;;;;;
                    (command "layer" "set" "pg" "")
                    (command "line" pg1 pt "")    
                    (setq textx (car pt))    
                    (setq texty originy) 
                    (setq ptxt (list textx texty)) 
                    (setq ptxt (polar ptxt (/ (* -13 pi) 24) 35.0))
               ;;;;;;;كتابة المحطات ومنسوب الخط التصميمي  ;;;;;;;;;;;;;;;;;    
                    (command "text" "j" "ml" ptxt 5.0 90.0 (rtos y 2 3)) 
                    (setq s (+ s station))
                    (setq pg1 pt)    
              )
     ;;;;;;;;;;;;;;;;;;;;;;;;إكتب الجريد الأخير;;;;;;;;;;;;;;;;;;;;
		   (setq pgi (list (+ xx1 50)  (- pviy 40)))
 		   (command "text" "J" "ML" pgi 5.0 0.0 (strcat "G = "  (RTOS G1 2 5)) )
)
