(DEFUN C:1 (/ GP) (SETQ GP (SSGET)) (COMMAND "CHANGE" GP "" "P" "C" "1" ""))
(DEFUN C:2 (/ GP) (SETQ GP (SSGET)) (COMMAND "CHANGE" GP "" "P" "C" "2" ""))
(DEFUN C:3 (/ GP) (SETQ GP (SSGET)) (COMMAND "CHANGE" GP "" "P" "C" "3" ""))
(DEFUN C:4 (/ GP) (SETQ GP (SSGET)) (COMMAND "CHANGE" GP "" "P" "C" "4" ""))
(DEFUN C:5 (/ GP) (SETQ GP (SSGET)) (COMMAND "CHANGE" GP "" "P" "C" "5" ""))
(DEFUN C:6 (/ GP) (SETQ GP (SSGET)) (COMMAND "CHANGE" GP "" "P" "C" "6" ""))
(DEFUN C:7 (/ GP) (SETQ GP (SSGET)) (COMMAND "CHANGE" GP "" "P" "C" "7" ""))
(DEFUN C:8 (/ GP) (SETQ GP (SSGET)) (COMMAND "CHANGE" GP "" "P" "C" "8" ""))
(DEFUN C:9 (/ GP) (SETQ GP (SSGET)) (COMMAND "CHANGE" GP "" "P" "C" "9" ""))
(DEFUN C:10 (/ GP) (SETQ GP (SSGET)) (COMMAND "CHANGE" GP "" "P" "C" "10" ""))
(DEFUN C:11 (/ GP) (SETQ GP (SSGET)) (COMMAND "CHANGE" GP "" "P" "C" "11" ""))
(DEFUN C:12 (/ GP) (SETQ GP (SSGET)) (COMMAND "CHANGE" GP "" "P" "C" "12" ""))
(DEFUN C:13 (/ GP) (SETQ GP (SSGET)) (COMMAND "CHANGE" GP "" "P" "C" "13" ""))
(DEFUN C:14 (/ GP) (SETQ GP (SSGET)) (COMMAND "CHANGE" GP "" "P" "C" "14" ""))
(DEFUN C:15 (/ GP) (SETQ GP (SSGET)) (COMMAND "CHANGE" GP "" "P" "C" "15" ""))
(DEFUN C:16 (/ GP) (SETQ GP (SSGET)) (COMMAND "CHANGE" GP "" "P" "C" "16" ""))
(DEFUN C:17 (/ GP) (SETQ GP (SSGET)) (COMMAND "CHANGE" GP "" "P" "C" "17" ""))
(DEFUN C:18 (/ GP) (SETQ GP (SSGET)) (COMMAND "CHANGE" GP "" "P" "C" "18" ""))
(DEFUN C:19 (/ GP) (SETQ GP (SSGET)) (COMMAND "CHANGE" GP "" "P" "C" "19" ""))
(DEFUN C:20 (/ GP) (SETQ GP (SSGET)) (COMMAND "CHANGE" GP "" "P" "C" "20" ""))
(DEFUN C:21 (/ GP) (SETQ GP (SSGET)) (COMMAND "CHANGE" GP "" "P" "C" "21" ""))
(DEFUN C:22 (/ GP) (SETQ GP (SSGET)) (COMMAND "CHANGE" GP "" "P" "C" "22" ""))
(DEFUN C:23 (/ GP) (SETQ GP (SSGET)) (COMMAND "CHANGE" GP "" "P" "C" "23" ""))
(DEFUN C:24 (/ GP) (SETQ GP (SSGET)) (COMMAND "CHANGE" GP "" "P" "C" "24" ""))
(DEFUN C:25 (/ GP) (SETQ GP (SSGET)) (COMMAND "CHANGE" GP "" "P" "C" "25" ""))
(DEFUN C:26 (/ GP) (SETQ GP (SSGET)) (COMMAND "CHANGE" GP "" "P" "C" "26" ""))
(DEFUN C:27 (/ GP) (SETQ GP (SSGET)) (COMMAND "CHANGE" GP "" "P" "C" "27" ""))
(DEFUN C:28 (/ GP) (SETQ GP (SSGET)) (COMMAND "CHANGE" GP "" "P" "C" "28" ""))
(DEFUN C:29 (/ GP) (SETQ GP (SSGET)) (COMMAND "CHANGE" GP "" "P" "C" "29" ""))
(DEFUN C:30 (/ GP) (SETQ GP (SSGET)) (COMMAND "CHANGE" GP "" "P" "C" "30" ""))
(DEFUN C:31 (/ GP) (SETQ GP (SSGET)) (COMMAND "CHANGE" GP "" "P" "C" "31" ""))
(DEFUN C:32 (/ GP) (SETQ GP (SSGET)) (COMMAND "CHANGE" GP "" "P" "C" "32" ""))
(DEFUN C:33 (/ GP) (SETQ GP (SSGET)) (COMMAND "CHANGE" GP "" "P" "C" "33" ""))
(DEFUN C:34 (/ GP) (SETQ GP (SSGET)) (COMMAND "CHANGE" GP "" "P" "C" "34" ""))
(DEFUN C:35 (/ GP) (SETQ GP (SSGET)) (COMMAND "CHANGE" GP "" "P" "C" "35" ""))
(DEFUN C:36 (/ GP) (SETQ GP (SSGET)) (COMMAND "CHANGE" GP "" "P" "C" "36" ""))
(DEFUN C:37 (/ GP) (SETQ GP (SSGET)) (COMMAND "CHANGE" GP "" "P" "C" "37" ""))
(DEFUN C:38 (/ GP) (SETQ GP (SSGET)) (COMMAND "CHANGE" GP "" "P" "C" "38" ""))
(DEFUN C:39 (/ GP) (SETQ GP (SSGET)) (COMMAND "CHANGE" GP "" "P" "C" "39" ""))
(DEFUN C:40 (/ GP) (SETQ GP (SSGET)) (COMMAND "CHANGE" GP "" "P" "C" "40" ""))
(DEFUN C:41 (/ GP) (SETQ GP (SSGET)) (COMMAND "CHANGE" GP "" "P" "C" "41" ""))
(DEFUN C:42 (/ GP) (SETQ GP (SSGET)) (COMMAND "CHANGE" GP "" "P" "C" "42" ""))
(DEFUN C:43 (/ GP) (SETQ GP (SSGET)) (COMMAND "CHANGE" GP "" "P" "C" "43" ""))
(DEFUN C:44 (/ GP) (SETQ GP (SSGET)) (COMMAND "CHANGE" GP "" "P" "C" "44" ""))
(DEFUN C:45 (/ GP) (SETQ GP (SSGET)) (COMMAND "CHANGE" GP "" "P" "C" "45" ""))
(DEFUN C:46 (/ GP) (SETQ GP (SSGET)) (COMMAND "CHANGE" GP "" "P" "C" "46" ""))
(DEFUN C:47 (/ GP) (SETQ GP (SSGET)) (COMMAND "CHANGE" GP "" "P" "C" "47" ""))
(DEFUN C:48 (/ GP) (SETQ GP (SSGET)) (COMMAND "CHANGE" GP "" "P" "C" "48" ""))
(DEFUN C:49 (/ GP) (SETQ GP (SSGET)) (COMMAND "CHANGE" GP "" "P" "C" "49" ""))
(DEFUN C:50 (/ GP) (SETQ GP (SSGET)) (COMMAND "CHANGE" GP "" "P" "C" "50" ""))
(DEFUN C:51 (/ GP) (SETQ GP (SSGET)) (COMMAND "CHANGE" GP "" "P" "C" "51" ""))
(DEFUN C:52 (/ GP) (SETQ GP (SSGET)) (COMMAND "CHANGE" GP "" "P" "C" "52" ""))
(DEFUN C:53 (/ GP) (SETQ GP (SSGET)) (COMMAND "CHANGE" GP "" "P" "C" "53" ""))
(DEFUN C:54 (/ GP) (SETQ GP (SSGET)) (COMMAND "CHANGE" GP "" "P" "C" "54" ""))
(DEFUN C:55 (/ GP) (SETQ GP (SSGET)) (COMMAND "CHANGE" GP "" "P" "C" "55" ""))
(DEFUN C:56 (/ GP) (SETQ GP (SSGET)) (COMMAND "CHANGE" GP "" "P" "C" "56" ""))
(DEFUN C:57 (/ GP) (SETQ GP (SSGET)) (COMMAND "CHANGE" GP "" "P" "C" "57" ""))
(DEFUN C:58 (/ GP) (SETQ GP (SSGET)) (COMMAND "CHANGE" GP "" "P" "C" "58" ""))
(DEFUN C:59 (/ GP) (SETQ GP (SSGET)) (COMMAND "CHANGE" GP "" "P" "C" "59" ""))
(DEFUN C:60 (/ GP) (SETQ GP (SSGET)) (COMMAND "CHANGE" GP "" "P" "C" "60" ""))
(DEFUN C:61 (/ GP) (SETQ GP (SSGET)) (COMMAND "CHANGE" GP "" "P" "C" "61" ""))
(DEFUN C:62 (/ GP) (SETQ GP (SSGET)) (COMMAND "CHANGE" GP "" "P" "C" "62" ""))
(DEFUN C:63 (/ GP) (SETQ GP (SSGET)) (COMMAND "CHANGE" GP "" "P" "C" "63" ""))
(DEFUN C:64 (/ GP) (SETQ GP (SSGET)) (COMMAND "CHANGE" GP "" "P" "C" "64" ""))
(DEFUN C:65 (/ GP) (SETQ GP (SSGET)) (COMMAND "CHANGE" GP "" "P" "C" "65" ""))
(DEFUN C:66 (/ GP) (SETQ GP (SSGET)) (COMMAND "CHANGE" GP "" "P" "C" "66" ""))
(DEFUN C:67 (/ GP) (SETQ GP (SSGET)) (COMMAND "CHANGE" GP "" "P" "C" "67" ""))
(DEFUN C:68 (/ GP) (SETQ GP (SSGET)) (COMMAND "CHANGE" GP "" "P" "C" "68" ""))
(DEFUN C:69 (/ GP) (SETQ GP (SSGET)) (COMMAND "CHANGE" GP "" "P" "C" "69" ""))
(DEFUN C:70 (/ GP) (SETQ GP (SSGET)) (COMMAND "CHANGE" GP "" "P" "C" "70" ""))
(DEFUN C:71 (/ GP) (SETQ GP (SSGET)) (COMMAND "CHANGE" GP "" "P" "C" "71" ""))
(DEFUN C:72 (/ GP) (SETQ GP (SSGET)) (COMMAND "CHANGE" GP "" "P" "C" "72" ""))
(DEFUN C:73 (/ GP) (SETQ GP (SSGET)) (COMMAND "CHANGE" GP "" "P" "C" "73" ""))
(DEFUN C:74 (/ GP) (SETQ GP (SSGET)) (COMMAND "CHANGE" GP "" "P" "C" "74" ""))
(DEFUN C:75 (/ GP) (SETQ GP (SSGET)) (COMMAND "CHANGE" GP "" "P" "C" "75" ""))
(DEFUN C:76 (/ GP) (SETQ GP (SSGET)) (COMMAND "CHANGE" GP "" "P" "C" "76" ""))
(DEFUN C:77 (/ GP) (SETQ GP (SSGET)) (COMMAND "CHANGE" GP "" "P" "C" "77" ""))
(DEFUN C:78 (/ GP) (SETQ GP (SSGET)) (COMMAND "CHANGE" GP "" "P" "C" "78" ""))
(DEFUN C:79 (/ GP) (SETQ GP (SSGET)) (COMMAND "CHANGE" GP "" "P" "C" "79" ""))
(DEFUN C:80 (/ GP) (SETQ GP (SSGET)) (COMMAND "CHANGE" GP "" "P" "C" "80" ""))
(DEFUN C:81 (/ GP) (SETQ GP (SSGET)) (COMMAND "CHANGE" GP "" "P" "C" "81" ""))
(DEFUN C:82 (/ GP) (SETQ GP (SSGET)) (COMMAND "CHANGE" GP "" "P" "C" "82" ""))
(DEFUN C:83 (/ GP) (SETQ GP (SSGET)) (COMMAND "CHANGE" GP "" "P" "C" "83" ""))
(DEFUN C:84 (/ GP) (SETQ GP (SSGET)) (COMMAND "CHANGE" GP "" "P" "C" "84" ""))
(DEFUN C:85 (/ GP) (SETQ GP (SSGET)) (COMMAND "CHANGE" GP "" "P" "C" "85" ""))
(DEFUN C:86 (/ GP) (SETQ GP (SSGET)) (COMMAND "CHANGE" GP "" "P" "C" "86" ""))
(DEFUN C:87 (/ GP) (SETQ GP (SSGET)) (COMMAND "CHANGE" GP "" "P" "C" "87" ""))
(DEFUN C:88 (/ GP) (SETQ GP (SSGET)) (COMMAND "CHANGE" GP "" "P" "C" "88" ""))
(DEFUN C:89 (/ GP) (SETQ GP (SSGET)) (COMMAND "CHANGE" GP "" "P" "C" "89" ""))
(DEFUN C:90 (/ GP) (SETQ GP (SSGET)) (COMMAND "CHANGE" GP "" "P" "C" "90" ""))
(DEFUN C:91 (/ GP) (SETQ GP (SSGET)) (COMMAND "CHANGE" GP "" "P" "C" "91" ""))
(DEFUN C:92 (/ GP) (SETQ GP (SSGET)) (COMMAND "CHANGE" GP "" "P" "C" "92" ""))
(DEFUN C:93 (/ GP) (SETQ GP (SSGET)) (COMMAND "CHANGE" GP "" "P" "C" "93" ""))
(DEFUN C:94 (/ GP) (SETQ GP (SSGET)) (COMMAND "CHANGE" GP "" "P" "C" "94" ""))
(DEFUN C:95 (/ GP) (SETQ GP (SSGET)) (COMMAND "CHANGE" GP "" "P" "C" "95" ""))
(DEFUN C:96 (/ GP) (SETQ GP (SSGET)) (COMMAND "CHANGE" GP "" "P" "C" "96" ""))
(DEFUN C:97 (/ GP) (SETQ GP (SSGET)) (COMMAND "CHANGE" GP "" "P" "C" "97" ""))
(DEFUN C:98 (/ GP) (SETQ GP (SSGET)) (COMMAND "CHANGE" GP "" "P" "C" "98" ""))
(DEFUN C:99 (/ GP) (SETQ GP (SSGET)) (COMMAND "CHANGE" GP "" "P" "C" "99" ""))
(DEFUN C:100 (/ GP) (SETQ GP (SSGET)) (COMMAND "CHANGE" GP "" "P" "C" "100" ""))
(DEFUN C:101 (/ GP) (SETQ GP (SSGET)) (COMMAND "CHANGE" GP "" "P" "C" "101" ""))
(DEFUN C:102 (/ GP) (SETQ GP (SSGET)) (COMMAND "CHANGE" GP "" "P" "C" "102" ""))
(DEFUN C:103 (/ GP) (SETQ GP (SSGET)) (COMMAND "CHANGE" GP "" "P" "C" "103" ""))
(DEFUN C:104 (/ GP) (SETQ GP (SSGET)) (COMMAND "CHANGE" GP "" "P" "C" "104" ""))
(DEFUN C:105 (/ GP) (SETQ GP (SSGET)) (COMMAND "CHANGE" GP "" "P" "C" "105" ""))
(DEFUN C:106 (/ GP) (SETQ GP (SSGET)) (COMMAND "CHANGE" GP "" "P" "C" "106" ""))
(DEFUN C:107 (/ GP) (SETQ GP (SSGET)) (COMMAND "CHANGE" GP "" "P" "C" "107" ""))
(DEFUN C:108 (/ GP) (SETQ GP (SSGET)) (COMMAND "CHANGE" GP "" "P" "C" "108" ""))
(DEFUN C:109 (/ GP) (SETQ GP (SSGET)) (COMMAND "CHANGE" GP "" "P" "C" "109" ""))
(DEFUN C:110 (/ GP) (SETQ GP (SSGET)) (COMMAND "CHANGE" GP "" "P" "C" "110" ""))
(DEFUN C:111 (/ GP) (SETQ GP (SSGET)) (COMMAND "CHANGE" GP "" "P" "C" "111" ""))
(DEFUN C:112 (/ GP) (SETQ GP (SSGET)) (COMMAND "CHANGE" GP "" "P" "C" "112" ""))
(DEFUN C:113 (/ GP) (SETQ GP (SSGET)) (COMMAND "CHANGE" GP "" "P" "C" "113" ""))
(DEFUN C:114 (/ GP) (SETQ GP (SSGET)) (COMMAND "CHANGE" GP "" "P" "C" "114" ""))
(DEFUN C:115 (/ GP) (SETQ GP (SSGET)) (COMMAND "CHANGE" GP "" "P" "C" "115" ""))
(DEFUN C:116 (/ GP) (SETQ GP (SSGET)) (COMMAND "CHANGE" GP "" "P" "C" "116" ""))
(DEFUN C:117 (/ GP) (SETQ GP (SSGET)) (COMMAND "CHANGE" GP "" "P" "C" "117" ""))
(DEFUN C:118 (/ GP) (SETQ GP (SSGET)) (COMMAND "CHANGE" GP "" "P" "C" "118" ""))
(DEFUN C:119 (/ GP) (SETQ GP (SSGET)) (COMMAND "CHANGE" GP "" "P" "C" "119" ""))
(DEFUN C:120 (/ GP) (SETQ GP (SSGET)) (COMMAND "CHANGE" GP "" "P" "C" "120" ""))
(DEFUN C:121 (/ GP) (SETQ GP (SSGET)) (COMMAND "CHANGE" GP "" "P" "C" "121" ""))
(DEFUN C:122 (/ GP) (SETQ GP (SSGET)) (COMMAND "CHANGE" GP "" "P" "C" "122" ""))
(DEFUN C:123 (/ GP) (SETQ GP (SSGET)) (COMMAND "CHANGE" GP "" "P" "C" "123" ""))
(DEFUN C:124 (/ GP) (SETQ GP (SSGET)) (COMMAND "CHANGE" GP "" "P" "C" "124" ""))
(DEFUN C:125 (/ GP) (SETQ GP (SSGET)) (COMMAND "CHANGE" GP "" "P" "C" "125" ""))
(DEFUN C:126 (/ GP) (SETQ GP (SSGET)) (COMMAND "CHANGE" GP "" "P" "C" "126" ""))
(DEFUN C:127 (/ GP) (SETQ GP (SSGET)) (COMMAND "CHANGE" GP "" "P" "C" "127" ""))
(DEFUN C:128 (/ GP) (SETQ GP (SSGET)) (COMMAND "CHANGE" GP "" "P" "C" "128" ""))
(DEFUN C:129 (/ GP) (SETQ GP (SSGET)) (COMMAND "CHANGE" GP "" "P" "C" "129" ""))
(DEFUN C:130 (/ GP) (SETQ GP (SSGET)) (COMMAND "CHANGE" GP "" "P" "C" "130" ""))
(DEFUN C:131 (/ GP) (SETQ GP (SSGET)) (COMMAND "CHANGE" GP "" "P" "C" "131" ""))
(DEFUN C:132 (/ GP) (SETQ GP (SSGET)) (COMMAND "CHANGE" GP "" "P" "C" "132" ""))
(DEFUN C:133 (/ GP) (SETQ GP (SSGET)) (COMMAND "CHANGE" GP "" "P" "C" "133" ""))
(DEFUN C:134 (/ GP) (SETQ GP (SSGET)) (COMMAND "CHANGE" GP "" "P" "C" "134" ""))
(DEFUN C:135 (/ GP) (SETQ GP (SSGET)) (COMMAND "CHANGE" GP "" "P" "C" "135" ""))
(DEFUN C:136 (/ GP) (SETQ GP (SSGET)) (COMMAND "CHANGE" GP "" "P" "C" "136" ""))
(DEFUN C:137 (/ GP) (SETQ GP (SSGET)) (COMMAND "CHANGE" GP "" "P" "C" "137" ""))
(DEFUN C:138 (/ GP) (SETQ GP (SSGET)) (COMMAND "CHANGE" GP "" "P" "C" "138" ""))
(DEFUN C:139 (/ GP) (SETQ GP (SSGET)) (COMMAND "CHANGE" GP "" "P" "C" "139" ""))
(DEFUN C:140 (/ GP) (SETQ GP (SSGET)) (COMMAND "CHANGE" GP "" "P" "C" "140" ""))
(DEFUN C:141 (/ GP) (SETQ GP (SSGET)) (COMMAND "CHANGE" GP "" "P" "C" "141" ""))
(DEFUN C:142 (/ GP) (SETQ GP (SSGET)) (COMMAND "CHANGE" GP "" "P" "C" "142" ""))
(DEFUN C:143 (/ GP) (SETQ GP (SSGET)) (COMMAND "CHANGE" GP "" "P" "C" "143" ""))
(DEFUN C:144 (/ GP) (SETQ GP (SSGET)) (COMMAND "CHANGE" GP "" "P" "C" "144" ""))
(DEFUN C:145 (/ GP) (SETQ GP (SSGET)) (COMMAND "CHANGE" GP "" "P" "C" "145" ""))
(DEFUN C:146 (/ GP) (SETQ GP (SSGET)) (COMMAND "CHANGE" GP "" "P" "C" "146" ""))
(DEFUN C:147 (/ GP) (SETQ GP (SSGET)) (COMMAND "CHANGE" GP "" "P" "C" "147" ""))
(DEFUN C:148 (/ GP) (SETQ GP (SSGET)) (COMMAND "CHANGE" GP "" "P" "C" "148" ""))
(DEFUN C:149 (/ GP) (SETQ GP (SSGET)) (COMMAND "CHANGE" GP "" "P" "C" "149" ""))
(DEFUN C:150 (/ GP) (SETQ GP (SSGET)) (COMMAND "CHANGE" GP "" "P" "C" "150" ""))
(DEFUN C:151 (/ GP) (SETQ GP (SSGET)) (COMMAND "CHANGE" GP "" "P" "C" "151" ""))
(DEFUN C:152 (/ GP) (SETQ GP (SSGET)) (COMMAND "CHANGE" GP "" "P" "C" "152" ""))
(DEFUN C:153 (/ GP) (SETQ GP (SSGET)) (COMMAND "CHANGE" GP "" "P" "C" "153" ""))
(DEFUN C:154 (/ GP) (SETQ GP (SSGET)) (COMMAND "CHANGE" GP "" "P" "C" "154" ""))
(DEFUN C:155 (/ GP) (SETQ GP (SSGET)) (COMMAND "CHANGE" GP "" "P" "C" "155" ""))
(DEFUN C:156 (/ GP) (SETQ GP (SSGET)) (COMMAND "CHANGE" GP "" "P" "C" "156" ""))
(DEFUN C:157 (/ GP) (SETQ GP (SSGET)) (COMMAND "CHANGE" GP "" "P" "C" "157" ""))
(DEFUN C:158 (/ GP) (SETQ GP (SSGET)) (COMMAND "CHANGE" GP "" "P" "C" "158" ""))
(DEFUN C:159 (/ GP) (SETQ GP (SSGET)) (COMMAND "CHANGE" GP "" "P" "C" "159" ""))
(DEFUN C:160 (/ GP) (SETQ GP (SSGET)) (COMMAND "CHANGE" GP "" "P" "C" "160" ""))
(DEFUN C:161 (/ GP) (SETQ GP (SSGET)) (COMMAND "CHANGE" GP "" "P" "C" "161" ""))
(DEFUN C:162 (/ GP) (SETQ GP (SSGET)) (COMMAND "CHANGE" GP "" "P" "C" "162" ""))
(DEFUN C:163 (/ GP) (SETQ GP (SSGET)) (COMMAND "CHANGE" GP "" "P" "C" "163" ""))
(DEFUN C:164 (/ GP) (SETQ GP (SSGET)) (COMMAND "CHANGE" GP "" "P" "C" "164" ""))
(DEFUN C:165 (/ GP) (SETQ GP (SSGET)) (COMMAND "CHANGE" GP "" "P" "C" "165" ""))
(DEFUN C:166 (/ GP) (SETQ GP (SSGET)) (COMMAND "CHANGE" GP "" "P" "C" "166" ""))
(DEFUN C:167 (/ GP) (SETQ GP (SSGET)) (COMMAND "CHANGE" GP "" "P" "C" "167" ""))
(DEFUN C:168 (/ GP) (SETQ GP (SSGET)) (COMMAND "CHANGE" GP "" "P" "C" "168" ""))
(DEFUN C:169 (/ GP) (SETQ GP (SSGET)) (COMMAND "CHANGE" GP "" "P" "C" "169" ""))
(DEFUN C:170 (/ GP) (SETQ GP (SSGET)) (COMMAND "CHANGE" GP "" "P" "C" "170" ""))
(DEFUN C:171 (/ GP) (SETQ GP (SSGET)) (COMMAND "CHANGE" GP "" "P" "C" "171" ""))
(DEFUN C:172 (/ GP) (SETQ GP (SSGET)) (COMMAND "CHANGE" GP "" "P" "C" "172" ""))
(DEFUN C:173 (/ GP) (SETQ GP (SSGET)) (COMMAND "CHANGE" GP "" "P" "C" "173" ""))
(DEFUN C:174 (/ GP) (SETQ GP (SSGET)) (COMMAND "CHANGE" GP "" "P" "C" "174" ""))
(DEFUN C:175 (/ GP) (SETQ GP (SSGET)) (COMMAND "CHANGE" GP "" "P" "C" "175" ""))
(DEFUN C:176 (/ GP) (SETQ GP (SSGET)) (COMMAND "CHANGE" GP "" "P" "C" "176" ""))
(DEFUN C:177 (/ GP) (SETQ GP (SSGET)) (COMMAND "CHANGE" GP "" "P" "C" "177" ""))
(DEFUN C:178 (/ GP) (SETQ GP (SSGET)) (COMMAND "CHANGE" GP "" "P" "C" "178" ""))
(DEFUN C:179 (/ GP) (SETQ GP (SSGET)) (COMMAND "CHANGE" GP "" "P" "C" "179" ""))
(DEFUN C:180 (/ GP) (SETQ GP (SSGET)) (COMMAND "CHANGE" GP "" "P" "C" "180" ""))
(DEFUN C:181 (/ GP) (SETQ GP (SSGET)) (COMMAND "CHANGE" GP "" "P" "C" "181" ""))
(DEFUN C:182 (/ GP) (SETQ GP (SSGET)) (COMMAND "CHANGE" GP "" "P" "C" "182" ""))
(DEFUN C:183 (/ GP) (SETQ GP (SSGET)) (COMMAND "CHANGE" GP "" "P" "C" "183" ""))
(DEFUN C:184 (/ GP) (SETQ GP (SSGET)) (COMMAND "CHANGE" GP "" "P" "C" "184" ""))
(DEFUN C:185 (/ GP) (SETQ GP (SSGET)) (COMMAND "CHANGE" GP "" "P" "C" "185" ""))
(DEFUN C:186 (/ GP) (SETQ GP (SSGET)) (COMMAND "CHANGE" GP "" "P" "C" "186" ""))
(DEFUN C:187 (/ GP) (SETQ GP (SSGET)) (COMMAND "CHANGE" GP "" "P" "C" "187" ""))
(DEFUN C:188 (/ GP) (SETQ GP (SSGET)) (COMMAND "CHANGE" GP "" "P" "C" "188" ""))
(DEFUN C:189 (/ GP) (SETQ GP (SSGET)) (COMMAND "CHANGE" GP "" "P" "C" "189" ""))
(DEFUN C:190 (/ GP) (SETQ GP (SSGET)) (COMMAND "CHANGE" GP "" "P" "C" "190" ""))
(DEFUN C:191 (/ GP) (SETQ GP (SSGET)) (COMMAND "CHANGE" GP "" "P" "C" "191" ""))
(DEFUN C:192 (/ GP) (SETQ GP (SSGET)) (COMMAND "CHANGE" GP "" "P" "C" "192" ""))
(DEFUN C:193 (/ GP) (SETQ GP (SSGET)) (COMMAND "CHANGE" GP "" "P" "C" "193" ""))
(DEFUN C:194 (/ GP) (SETQ GP (SSGET)) (COMMAND "CHANGE" GP "" "P" "C" "194" ""))
(DEFUN C:195 (/ GP) (SETQ GP (SSGET)) (COMMAND "CHANGE" GP "" "P" "C" "195" ""))
(DEFUN C:196 (/ GP) (SETQ GP (SSGET)) (COMMAND "CHANGE" GP "" "P" "C" "196" ""))
(DEFUN C:197 (/ GP) (SETQ GP (SSGET)) (COMMAND "CHANGE" GP "" "P" "C" "197" ""))
(DEFUN C:198 (/ GP) (SETQ GP (SSGET)) (COMMAND "CHANGE" GP "" "P" "C" "198" ""))
(DEFUN C:199 (/ GP) (SETQ GP (SSGET)) (COMMAND "CHANGE" GP "" "P" "C" "199" ""))
(DEFUN C:200 (/ GP) (SETQ GP (SSGET)) (COMMAND "CHANGE" GP "" "P" "C" "200" ""))
(DEFUN C:201 (/ GP) (SETQ GP (SSGET)) (COMMAND "CHANGE" GP "" "P" "C" "201" ""))
(DEFUN C:202 (/ GP) (SETQ GP (SSGET)) (COMMAND "CHANGE" GP "" "P" "C" "202" ""))
(DEFUN C:203 (/ GP) (SETQ GP (SSGET)) (COMMAND "CHANGE" GP "" "P" "C" "203" ""))
(DEFUN C:204 (/ GP) (SETQ GP (SSGET)) (COMMAND "CHANGE" GP "" "P" "C" "204" ""))
(DEFUN C:205 (/ GP) (SETQ GP (SSGET)) (COMMAND "CHANGE" GP "" "P" "C" "205" ""))
(DEFUN C:206 (/ GP) (SETQ GP (SSGET)) (COMMAND "CHANGE" GP "" "P" "C" "206" ""))
(DEFUN C:207 (/ GP) (SETQ GP (SSGET)) (COMMAND "CHANGE" GP "" "P" "C" "207" ""))
(DEFUN C:208 (/ GP) (SETQ GP (SSGET)) (COMMAND "CHANGE" GP "" "P" "C" "208" ""))
(DEFUN C:209 (/ GP) (SETQ GP (SSGET)) (COMMAND "CHANGE" GP "" "P" "C" "209" ""))
(DEFUN C:210 (/ GP) (SETQ GP (SSGET)) (COMMAND "CHANGE" GP "" "P" "C" "210" ""))
(DEFUN C:211 (/ GP) (SETQ GP (SSGET)) (COMMAND "CHANGE" GP "" "P" "C" "211" ""))
(DEFUN C:212 (/ GP) (SETQ GP (SSGET)) (COMMAND "CHANGE" GP "" "P" "C" "212" ""))
(DEFUN C:213 (/ GP) (SETQ GP (SSGET)) (COMMAND "CHANGE" GP "" "P" "C" "213" ""))
(DEFUN C:214 (/ GP) (SETQ GP (SSGET)) (COMMAND "CHANGE" GP "" "P" "C" "214" ""))
(DEFUN C:215 (/ GP) (SETQ GP (SSGET)) (COMMAND "CHANGE" GP "" "P" "C" "215" ""))
(DEFUN C:216 (/ GP) (SETQ GP (SSGET)) (COMMAND "CHANGE" GP "" "P" "C" "216" ""))
(DEFUN C:217 (/ GP) (SETQ GP (SSGET)) (COMMAND "CHANGE" GP "" "P" "C" "217" ""))
(DEFUN C:218 (/ GP) (SETQ GP (SSGET)) (COMMAND "CHANGE" GP "" "P" "C" "218" ""))
(DEFUN C:219 (/ GP) (SETQ GP (SSGET)) (COMMAND "CHANGE" GP "" "P" "C" "219" ""))
(DEFUN C:220 (/ GP) (SETQ GP (SSGET)) (COMMAND "CHANGE" GP "" "P" "C" "220" ""))
(DEFUN C:221 (/ GP) (SETQ GP (SSGET)) (COMMAND "CHANGE" GP "" "P" "C" "221" ""))
(DEFUN C:222 (/ GP) (SETQ GP (SSGET)) (COMMAND "CHANGE" GP "" "P" "C" "222" ""))
(DEFUN C:223 (/ GP) (SETQ GP (SSGET)) (COMMAND "CHANGE" GP "" "P" "C" "223" ""))
(DEFUN C:224 (/ GP) (SETQ GP (SSGET)) (COMMAND "CHANGE" GP "" "P" "C" "224" ""))
(DEFUN C:225 (/ GP) (SETQ GP (SSGET)) (COMMAND "CHANGE" GP "" "P" "C" "225" ""))
(DEFUN C:226 (/ GP) (SETQ GP (SSGET)) (COMMAND "CHANGE" GP "" "P" "C" "226" ""))
(DEFUN C:227 (/ GP) (SETQ GP (SSGET)) (COMMAND "CHANGE" GP "" "P" "C" "227" ""))
(DEFUN C:228 (/ GP) (SETQ GP (SSGET)) (COMMAND "CHANGE" GP "" "P" "C" "228" ""))
(DEFUN C:229 (/ GP) (SETQ GP (SSGET)) (COMMAND "CHANGE" GP "" "P" "C" "229" ""))
(DEFUN C:230 (/ GP) (SETQ GP (SSGET)) (COMMAND "CHANGE" GP "" "P" "C" "230" ""))
(DEFUN C:231 (/ GP) (SETQ GP (SSGET)) (COMMAND "CHANGE" GP "" "P" "C" "231" ""))
(DEFUN C:232 (/ GP) (SETQ GP (SSGET)) (COMMAND "CHANGE" GP "" "P" "C" "232" ""))
(DEFUN C:233 (/ GP) (SETQ GP (SSGET)) (COMMAND "CHANGE" GP "" "P" "C" "233" ""))
(DEFUN C:234 (/ GP) (SETQ GP (SSGET)) (COMMAND "CHANGE" GP "" "P" "C" "234" ""))
(DEFUN C:235 (/ GP) (SETQ GP (SSGET)) (COMMAND "CHANGE" GP "" "P" "C" "235" ""))
(DEFUN C:236 (/ GP) (SETQ GP (SSGET)) (COMMAND "CHANGE" GP "" "P" "C" "236" ""))
(DEFUN C:237 (/ GP) (SETQ GP (SSGET)) (COMMAND "CHANGE" GP "" "P" "C" "237" ""))
(DEFUN C:238 (/ GP) (SETQ GP (SSGET)) (COMMAND "CHANGE" GP "" "P" "C" "238" ""))
(DEFUN C:239 (/ GP) (SETQ GP (SSGET)) (COMMAND "CHANGE" GP "" "P" "C" "239" ""))
(DEFUN C:240 (/ GP) (SETQ GP (SSGET)) (COMMAND "CHANGE" GP "" "P" "C" "240" ""))
(DEFUN C:241 (/ GP) (SETQ GP (SSGET)) (COMMAND "CHANGE" GP "" "P" "C" "241" ""))
(DEFUN C:242 (/ GP) (SETQ GP (SSGET)) (COMMAND "CHANGE" GP "" "P" "C" "242" ""))
(DEFUN C:243 (/ GP) (SETQ GP (SSGET)) (COMMAND "CHANGE" GP "" "P" "C" "243" ""))
(DEFUN C:244 (/ GP) (SETQ GP (SSGET)) (COMMAND "CHANGE" GP "" "P" "C" "244" ""))
(DEFUN C:245 (/ GP) (SETQ GP (SSGET)) (COMMAND "CHANGE" GP "" "P" "C" "245" ""))
(DEFUN C:246 (/ GP) (SETQ GP (SSGET)) (COMMAND "CHANGE" GP "" "P" "C" "246" ""))
(DEFUN C:247 (/ GP) (SETQ GP (SSGET)) (COMMAND "CHANGE" GP "" "P" "C" "247" ""))
(DEFUN C:248 (/ GP) (SETQ GP (SSGET)) (COMMAND "CHANGE" GP "" "P" "C" "248" ""))
(DEFUN C:249 (/ GP) (SETQ GP (SSGET)) (COMMAND "CHANGE" GP "" "P" "C" "249" ""))
(DEFUN C:250 (/ GP) (SETQ GP (SSGET)) (COMMAND "CHANGE" GP "" "P" "C" "250" ""))
(DEFUN C:251 (/ GP) (SETQ GP (SSGET)) (COMMAND "CHANGE" GP "" "P" "C" "251" ""))
(DEFUN C:252 (/ GP) (SETQ GP (SSGET)) (COMMAND "CHANGE" GP "" "P" "C" "252" ""))
(DEFUN C:253 (/ GP) (SETQ GP (SSGET)) (COMMAND "CHANGE" GP "" "P" "C" "253" ""))
(DEFUN C:254 (/ GP) (SETQ GP (SSGET)) (COMMAND "CHANGE" GP "" "P" "C" "254" ""))
(DEFUN C:255 (/ GP) (SETQ GP (SSGET)) (COMMAND "CHANGE" GP "" "P" "C" "255" ""))
(defun c:nc()
     (while
       (setq e(entsel "\nselect the object:"))
         (setq a(assoc 8(entget(car e)))
               b(cdr a)
         )
         (command "layer" "m" b "")
        )
       )
