(defun c:txtla();(select a text and lisp will create a new layer for the same with same name)
  (setq ss(ssget))
  (setq len(sslength ss))
  (setq co 0)
  (repeat len
    (setq ent(ssname ss co))
    (setq lis(entget ent))
    (setq code(cdr(assoc 1 lis)))
    (command "layer" "n" code "")
    (command "chprop" ent "" "la" code "")
    (setq co(+ co 1))
    )
  )
