;;; This lisp will move the whole drawing to the Co-ordinate.
(defun c:mco ()
(setq sel(ssget "x"))
(setvar "osmode" 32)
(setq pt(getpoint "\nPick intersection point: "))
(setvar "osmode" 0)
(setq x_co(getREAL "\nEnter X co-ordinate: "))
(setq y_co(getREAL "\nEnter Y co-ordinate: "))
(setq x_cal(* x_co 0.5))
(setq y_cal(* y_co 0.5))
(setq spt (list x_cal y_cal))
(command "move" sel "" pt spt)(princ))
