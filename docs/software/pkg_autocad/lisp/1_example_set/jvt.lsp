;kwais?
(DEFUN C:1   ()  (SETQ SS (SSGET)) (COMMAND "CHANGE" "P" "" "P" "C" "1" ""))
(DEFUN C:2   ()  (SETQ SS (SSGET)) (COMMAND "CHANGE" "P" "" "P" "C" "2" ""))
(DEFUN C:3   ()  (SETQ SS (SSGET)) (COMMAND "CHANGE" "P" "" "P" "C" "3" ""))
(DEFUN C:4   ()  (SETQ SS (SSGET)) (COMMAND "CHANGE" "P" "" "P" "C" "4" ""))
(DEFUN C:5   ()  (SETQ SS (SSGET)) (COMMAND "CHANGE" "P" "" "P" "C" "5" ""))
(DEFUN C:6   ()  (SETQ SS (SSGET)) (COMMAND "CHANGE" "P" "" "P" "C" "6" ""))
(DEFUN C:7   ()  (SETQ SS (SSGET)) (COMMAND "CHANGE" "P" "" "P" "C" "7" ""))
(DEFUN C:8   ()  (SETQ SS (SSGET)) (COMMAND "CHANGE" "P" "" "P" "C" "8" ""))
(DEFUN C:9   ()  (SETQ SS (SSGET)) (COMMAND "CHANGE" "P" "" "P" "C" "9" ""))
(DEFUN C:10  ()  (SETQ SS (SSGET)) (COMMAND "CHANGE" "P" "" "P" "C" "10" ""))
(DEFUN C:11  ()  (SETQ SS (SSGET)) (COMMAND "CHANGE" "P" "" "P" "C" "11" ""))
(DEFUN C:12  ()  (SETQ SS (SSGET)) (COMMAND "CHANGE" "P" "" "P" "C" "12" ""))
(DEFUN C:13  ()  (SETQ SS (SSGET)) (COMMAND "CHANGE" "P" "" "P" "C" "13" ""))
(DEFUN C:14  ()  (SETQ SS (SSGET)) (COMMAND "CHANGE" "P" "" "P" "C" "14" ""))
(DEFUN C:15  ()  (SETQ SS (SSGET)) (COMMAND "CHANGE" "P" "" "P" "C" "15" ""))
(DEFUN C:254  ()  (SETQ SS (SSGET)) (COMMAND "CHANGE" "P" "" "P" "C" "254" ""))
(DEFUN C:253  ()  (SETQ SS (SSGET)) (COMMAND "CHANGE" "P" "" "P" "C" "253" ""))
(DEFUN C:252  ()  (SETQ SS (SSGET)) (COMMAND "CHANGE" "P" "" "P" "C" "252" ""))
(DEFUN C:251  ()  (SETQ SS (SSGET)) (COMMAND "CHANGE" "P" "" "P" "C" "251" ""))
(DEFUN C:250  ()  (SETQ SS (SSGET)) (COMMAND "CHANGE" "P" "" "P" "C" "250" ""))
(DEFUN C:V1  ()  (SETQ SS (SSGET)) (COMMAND "CHANGE" "P" "" "P" "C" "241" ""))
(DEFUN C:V2  ()  (SETQ SS (SSGET)) (COMMAND "CHANGE" "P" "" "P" "C" "231" ""))
(DEFUN C:V3  ()  (SETQ SS (SSGET)) (COMMAND "CHANGE" "P" "" "P" "C" "221" ""))
(DEFUN C:V4  ()  (SETQ SS (SSGET)) (COMMAND "CHANGE" "P" "" "P" "C" "210" ""))
(DEFUN C:V5  ()  (SETQ SS (SSGET)) (COMMAND "CHANGE" "P" "" "P" "C" "212" ""))
(DEFUN C:V6  ()  (SETQ SS (SSGET)) (COMMAND "CHANGE" "P" "" "P" "C" "202" ""))
(DEFUN C:V7  ()  (SETQ SS (SSGET)) (COMMAND "CHANGE" "P" "" "P" "C" "214" ""))
(DEFUN C:V8  ()  (SETQ SS (SSGET)) (COMMAND "CHANGE" "P" "" "P" "C" "216" ""))
(DEFUN C:V9  ()  (SETQ SS (SSGET)) (COMMAND "CHANGE" "P" "" "P" "C" "206" ""))
(DEFUN C:V10  ()  (SETQ SS (SSGET)) (COMMAND "CHANGE" "P" "" "P" "C" "208" ""))
(DEFUN C:V11  ()  (SETQ SS (SSGET)) (COMMAND "CHANGE" "P" "" "P" "C" "198" ""))
(DEFUN C:V12  ()  (SETQ SS (SSGET)) (COMMAND "CHANGE" "P" "" "P" "C" "188" ""))
(DEFUN C:R1  ()  (SETQ SS (SSGET)) (COMMAND "CHANGE" "P" "" "P" "C" "31" ""))
(DEFUN C:R2  ()  (SETQ SS (SSGET)) (COMMAND "CHANGE" "P" "" "P" "C" "21" ""))
(DEFUN C:R3  ()  (SETQ SS (SSGET)) (COMMAND "CHANGE" "P" "" "P" "C" "11" ""))
(DEFUN C:R4  ()  (SETQ SS (SSGET)) (COMMAND "CHANGE" "P" "" "P" "C" "32" ""))
(DEFUN C:R5  ()  (SETQ SS (SSGET)) (COMMAND "CHANGE" "P" "" "P" "C" "30" ""))
(DEFUN C:R6  ()  (SETQ SS (SSGET)) (COMMAND "CHANGE" "P" "" "P" "C" "20" ""))
(DEFUN C:R7  ()  (SETQ SS (SSGET)) (COMMAND "CHANGE" "P" "" "P" "C" "10" ""))
(DEFUN C:R8  ()  (SETQ SS (SSGET)) (COMMAND "CHANGE" "P" "" "P" "C" "22" ""))
(DEFUN C:R9  ()  (SETQ SS (SSGET)) (COMMAND "CHANGE" "P" "" "P" "C" "24" ""))
(DEFUN C:R10  ()  (SETQ SS (SSGET)) (COMMAND "CHANGE" "P" "" "P" "C" "14" ""))
(DEFUN C:R11  ()  (SETQ SS (SSGET)) (COMMAND "CHANGE" "P" "" "P" "C" "16" ""))
(DEFUN C:R12  ()  (SETQ SS (SSGET)) (COMMAND "CHANGE" "P" "" "P" "C" "18" ""))
(DEFUN C:Y1  ()  (SETQ SS (SSGET)) (COMMAND "CHANGE" "P" "" "P" "C" "61" ""))
(DEFUN C:Y2  ()  (SETQ SS (SSGET)) (COMMAND "CHANGE" "P" "" "P" "C" "51" ""))
(DEFUN C:Y3  ()  (SETQ SS (SSGET)) (COMMAND "CHANGE" "P" "" "P" "C" "41" ""))
(DEFUN C:Y4  ()  (SETQ SS (SSGET)) (COMMAND "CHANGE" "P" "" "P" "C" "50" ""))
(DEFUN C:Y5  ()  (SETQ SS (SSGET)) (COMMAND "CHANGE" "P" "" "P" "C" "52" ""))
(DEFUN C:Y6  ()  (SETQ SS (SSGET)) (COMMAND "CHANGE" "P" "" "P" "C" "54" ""))
(DEFUN C:Y7  ()  (SETQ SS (SSGET)) (COMMAND "CHANGE" "P" "" "P" "C" "56" ""))
(DEFUN C:Y8  ()  (SETQ SS (SSGET)) (COMMAND "CHANGE" "P" "" "P" "C" "58" ""))
(DEFUN C:Y9  ()  (SETQ SS (SSGET)) (COMMAND "CHANGE" "P" "" "P" "C" "48" ""))
(DEFUN C:Y10  ()  (SETQ SS (SSGET)) (COMMAND "CHANGE" "P" "" "P" "C" "38" ""))
(DEFUN C:Y11  ()  (SETQ SS (SSGET)) (COMMAND "CHANGE" "P" "" "P" "C" "19" ""))
(DEFUN C:Y12  ()  (SETQ SS (SSGET)) (COMMAND "CHANGE" "P" "" "P" "C" "28" ""))
(DEFUN C:G1  ()  (SETQ SS (SSGET)) (COMMAND "CHANGE" "P" "" "P" "C" "71" ""))
(DEFUN C:G2  ()  (SETQ SS (SSGET)) (COMMAND "CHANGE" "P" "" "P" "C" "81" ""))
(DEFUN C:G3  ()  (SETQ SS (SSGET)) (COMMAND "CHANGE" "P" "" "P" "C" "70" ""))
(DEFUN C:G4  ()  (SETQ SS (SSGET)) (COMMAND "CHANGE" "P" "" "P" "C" "80" ""))
(DEFUN C:G5  ()  (SETQ SS (SSGET)) (COMMAND "CHANGE" "P" "" "P" "C" "82" ""))
(DEFUN C:G6  ()  (SETQ SS (SSGET)) (COMMAND "CHANGE" "P" "" "P" "C" "90" ""))
(DEFUN C:G7  ()  (SETQ SS (SSGET)) (COMMAND "CHANGE" "P" "" "P" "C" "100" ""))
(DEFUN C:G8  ()  (SETQ SS (SSGET)) (COMMAND "CHANGE" "P" "" "P" "C" "92" ""))
(DEFUN C:G9  ()  (SETQ SS (SSGET)) (COMMAND "CHANGE" "P" "" "P" "C" "94" ""))
(DEFUN C:G10  ()  (SETQ SS (SSGET)) (COMMAND "CHANGE" "P" "" "P" "C" "96" ""))
(DEFUN C:G11  ()  (SETQ SS (SSGET)) (COMMAND "CHANGE" "P" "" "P" "C" "98" ""))
(DEFUN C:G12  ()  (SETQ SS (SSGET)) (COMMAND "CHANGE" "P" "" "P" "C" "108" ""))
(DEFUN C:B1  ()  (SETQ SS (SSGET)) (COMMAND "CHANGE" "P" "" "P" "C" "121" ""))
(DEFUN C:B2  ()  (SETQ SS (SSGET)) (COMMAND "CHANGE" "P" "" "P" "C" "141" ""))
(DEFUN C:B3  ()  (SETQ SS (SSGET)) (COMMAND "CHANGE" "P" "" "P" "C" "151" ""))
(DEFUN C:B4  ()  (SETQ SS (SSGET)) (COMMAND "CHANGE" "P" "" "P" "C" "130" ""))
(DEFUN C:B5  ()  (SETQ SS (SSGET)) (COMMAND "CHANGE" "P" "" "P" "C" "140" ""))
(DEFUN C:B6  ()  (SETQ SS (SSGET)) (COMMAND "CHANGE" "P" "" "P" "C" "150" ""))
(DEFUN C:B7  ()  (SETQ SS (SSGET)) (COMMAND "CHANGE" "P" "" "P" "C" "152" ""))
(DEFUN C:B8  ()  (SETQ SS (SSGET)) (COMMAND "CHANGE" "P" "" "P" "C" "160" ""))
(DEFUN C:B9  ()  (SETQ SS (SSGET)) (COMMAND "CHANGE" "P" "" "P" "C" "170" ""))
(DEFUN C:B10  ()  (SETQ SS (SSGET)) (COMMAND "CHANGE" "P" "" "P" "C" "174" ""))
(DEFUN C:B11  ()  (SETQ SS (SSGET)) (COMMAND "CHANGE" "P" "" "P" "C" "176" ""))
(DEFUN C:B12  ()  (SETQ SS (SSGET)) (COMMAND "CHANGE" "P" "" "P" "C" "178" ""))
(DEFUN C:BW1  ()  (SETQ SS (SSGET)) (COMMAND "CHANGE" "P" "" "P" "C" "7" ""))
(DEFUN C:BW2  ()  (SETQ SS (SSGET)) (COMMAND "CHANGE" "P" "" "P" "C" "254" ""))
(DEFUN C:BW3  ()  (SETQ SS (SSGET)) (COMMAND "CHANGE" "P" "" "P" "C" "9" ""))
(DEFUN C:BW4  ()  (SETQ SS (SSGET)) (COMMAND "CHANGE" "P" "" "P" "C" "253" ""))
(DEFUN C:BW5  ()  (SETQ SS (SSGET)) (COMMAND "CHANGE" "P" "" "P" "C" "8" ""))
(DEFUN C:BW6  ()  (SETQ SS (SSGET)) (COMMAND "CHANGE" "P" "" "P" "C" "252" ""))
(DEFUN C:BW7  ()  (SETQ SS (SSGET)) (COMMAND "CHANGE" "P" "" "P" "C" "251" ""))
(DEFUN C:BW8  ()  (SETQ SS (SSGET)) (COMMAND "CHANGE" "P" "" "P" "C" "250" ""))
(DEFUN C:OB  ()  (SETQ SS (SSGET)) (COMMAND "CHANGE" "P" "" "P" "LA" "OBSTN" ""))
(DEFUN C:BT  ()  (SETQ SS (SSGET)) (COMMAND "CHANGE" "P" "" "P" "LA" "BTEXT" ""))
(DEFUN C:SD  ()  (SETQ SS (SSGET)) (COMMAND "CHANGE" "P" "" "P" "LA" "SD" ""))
(DEFUN C:TEL ()  (SETQ SS (SSGET)) (COMMAND "CHANGE" "P" "" "P" "LA" "TELE" ""))
(DEFUN C:ELE ()  (SETQ SS (SSGET)) (COMMAND "CHANGE" "P" "" "P" "LA" "ELEC" ""))
(DEFUN C:IRR ()  (SETQ SS (SSGET)) (COMMAND "CHANGE" "P" "" "P" "LA" "IRRIG" ""))
(DEFUN C:POT ()  (SETQ SS (SSGET)) (COMMAND "CHANGE" "P" "" "P" "LA" "POTABLE" ""))
(DEFUN C:SEW ()  (SETQ SS (SSGET)) (COMMAND "CHANGE" "P" "" "P" "LA" "SEWER" ""))
(DEFUN C:FPL ()  (SETQ SS (SSGET)) (COMMAND "CHANGE" "P" "" "P" "LA" "FUEL-PL" ""))
(DEFUN C:STL ()  (SETQ SS (SSGET)) (COMMAND "CHANGE" "P" "" "P" "LA" "STLT" ""))
(DEFUN C:SAN ()  (SETQ SS (SSGET)) (COMMAND "CHANGE" "P" "" "P" "LA" "SAN" ""))
(DEFUN C:RD  ()  (SETQ SS (SSGET)) (COMMAND "CHANGE" "P" "" "P" "LA" "ROAD" ""))
(DEFUN C:CD  ()  (SETQ SS (SSGET)) (COMMAND "CHANGE" "P" "" "P" "LA" "CD" ""))
(DEFUN C:REB ()  (SETQ SS (SSGET)) (COMMAND "CHANGE" "P" "" "P" "LA" "REBAR" ""))
(DEFUN C:LS  ()  (SETQ SS (SSGET)) (COMMAND "CHANGE" "P" "" "P" "LA" "LANDS" ""))
(DEFUN C:TT  ()  (SETQ SS (SSGET)) (COMMAND "CHANGE" "P" "" "P" "LA" "TEXT" ""))
(DEFUN C:CW  ()  (SETQ SS (SSGET)) (COMMAND "CHANGE" "P" "" "P" "LA" "CONWALL" ""))
(DEFUN C:BB  ()  (SETQ SS (SSGET)) (COMMAND "CHANGE" "P" "" "P" "LA" "BUBBLERS" ""))
(DEFUN C:HA  ()  (SETQ SS (SSGET)) (COMMAND "CHANGE" "P" "" "P" "LA" "HATCH" ""))
(DEFUN C:CL  ()  (SETQ SS (SSGET)) (COMMAND "CHANGE" "P" "" "P" "LA" "CL" ""))
(DEFUN C:DM  ()  (SETQ SS (SSGET)) (COMMAND "CHANGE" "P" "" "P" "LA" "DIM" ""))
(DEFUN C:WL  ()  (SETQ SS (SSGET)) (COMMAND "CHANGE" "P" "" "P" "LA" "WALLS" ""))
(DEFUN C:PP  ()  (SETQ SS (SSGET)) (COMMAND "CHANGE" "P" "" "P" "LA" "PIPES" ""))
(DEFUN C:TP  ()  (SETQ SS (SSGET)) (COMMAND "CHANGE" "P" "" "P" "LA" "T-PIT" ""))
(DEFUN C:RAD ()  (SETQ SS (SSGET)) (COMMAND "CHANGE" "P" "" "P" "LA" "RAD" ""))
(DEFUN C:CR  ()  (SETQ SS (SSGET)) (COMMAND "CHANGE" "P" "" "P" "LA" "CORD" ""))
(DEFUN C:EOC ()  (SETQ SS (SSGET)) (COMMAND "CHANGE" "P" "" "P" "LA" "EOC" ""))
(DEFUN C:HI  ()  (SETQ SS (SSGET)) (COMMAND "CHANGE" "P" "" "P" "LT" "HIDDEN" ""))
(DEFUN C:HI1 ()  (SETQ SS (SSGET)) (COMMAND "CHANGE" "P" "" "P" "LT" "HIDDEN2" ""))
(DEFUN C:HI2 ()  (SETQ SS (SSGET)) (COMMAND "CHANGE" "P" "" "P" "LT" "HIDDENX2" ""))
(DEFUN C:CEN ()  (SETQ SS (SSGET)) (COMMAND "CHANGE" "P" "" "P" "LT" "CENTER" ""))
(DEFUN C:CEN1 ()  (SETQ SS (SSGET)) (COMMAND "CHANGE" "P" "" "P" "LT" "CENTER2" ""))
(DEFUN C:CEN2 ()  (SETQ SS (SSGET)) (COMMAND "CHANGE" "P" "" "P" "LT" "CENTERX2" ""))
(DEFUN C:PH  ()  (SETQ SS (SSGET)) (COMMAND "CHANGE" "P" "" "P" "LT" "PHANTOM" ""))
(DEFUN C:PH1  ()  (SETQ SS (SSGET)) (COMMAND "CHANGE" "P" "" "P" "LT" "PHANTOM2" ""))
(DEFUN C:PH2  ()  (SETQ SS (SSGET)) (COMMAND "CHANGE" "P" "" "P" "LT" "PHANTOMX2" ""))
(DEFUN C:DS  ()  (SETQ SS (SSGET)) (COMMAND "CHANGE" "P" "" "P" "LT" "DASHDOT" ""))
(DEFUN C:DS1  ()  (SETQ SS (SSGET)) (COMMAND "CHANGE" "P" "" "P" "LT" "DASHDOT2" ""))
(DEFUN C:DS2  ()  (SETQ SS (SSGET)) (COMMAND "CHANGE" "P" "" "P" "LT" "DASHDOTX2" ""))
(DEFUN C:CN  ()  (SETQ SS (SSGET)) (COMMAND "CHANGE" "P" "" "P" "LT" "CONTINUOUS" ""))
(DEFUN C:HID ()  (SETQ SS (SSGET)) (COMMAND "CHANGE" "P" "" "P" "LT" "HID1" ""))
(DEFUN C:LG  ()  (SETQ SS (SSGET)) (COMMAND "CHANGE" "P" "" "P" "LT" "LIGHT" "")) 
(DEFUN C:DOT  ()  (SETQ SS (SSGET)) (COMMAND "CHANGE" "P" "" "P" "LT" "DOT" "")) 
(DEFUN C:DOT1  ()  (SETQ SS (SSGET)) (COMMAND "CHANGE" "P" "" "P" "LT" "DOT2" "")) 
(DEFUN C:DOT2  ()  (SETQ SS (SSGET)) (COMMAND "CHANGE" "P" "" "P" "LT" "DOTX2" "")) 
(DEFUN C:ZIG  ()  (SETQ SS (SSGET)) (COMMAND "CHANGE" "P" "" "P" "LT" "ZIGZAG" ""))
(DEFUN C:TRK  ()  (SETQ SS (SSGET)) (COMMAND "CHANGE" "P" "" "P" "LT" "TRACKS" ""))
(DEFUN C:BAT  ()  (SETQ SS (SSGET)) (COMMAND "CHANGE" "P" "" "P" "LT" "BATTING" ""))
(DEFUN C:FENCE  ()  (SETQ SS (SSGET)) (COMMAND "CHANGE" "P" "" "P" "LT" "TRACKS" ""))
(DEFUN C:FENCE1  ()  (SETQ SS (SSGET)) (COMMAND "CHANGE" "P" "" "P" "LT" "FENCELINE1" ""))
(DEFUN C:FENCE2  ()  (SETQ SS (SSGET)) (COMMAND "CHANGE" "P" "" "P" "LT" "FENCELINE2" ""))
(DEFUN C:FENCE3  ()  (SETQ SS (SSGET)) (COMMAND "CHANGE" "P" "" "P" "LT" "BATTING" ""))
(DEFUN C:L1  ()  (SETQ SS (SSGET)) (COMMAND "CHANGE" "P" "" "P" "LT" "FENCELINE1" ""))
(DEFUN C:L2  ()  (SETQ SS (SSGET)) (COMMAND "CHANGE" "P" "" "P" "LT" "FENCELINE2" ""))
(DEFUN C:L3  ()  (SETQ SS (SSGET)) (COMMAND "CHANGE" "P" "" "P" "LT" "tracks" ""))
(DEFUN C:L4  ()  (SETQ SS (SSGET)) (COMMAND "CHANGE" "P" "" "P" "LT" "zigzag" ""))
(DEFUN C:L5  ()  (SETQ SS (SSGET)) (COMMAND "CHANGE" "P" "" "P" "LT" "batting" ""))
(DEFUN C:L6  ()  (SETQ SS (SSGET)) (COMMAND "CHANGE" "P" "" "P" "LT" "GAS_LINE" ""))
(DEFUN C:L7  ()  (SETQ SS (SSGET)) (COMMAND "CHANGE" "P" "" "P" "LT" "HOT_WATER_SUPPLY" ""))
(DEFUN C:GAS  ()  (SETQ SS (SSGET)) (COMMAND "CHANGE" "P" "" "P" "LT" "GAS_LINE" ""))
(DEFUN C:HOT  ()  (SETQ SS (SSGET)) (COMMAND "CHANGE" "P" "" "P" "LT" "HOT_WATER_SUPPLY" ""))
(DEFUN C:CR  (/ gp) (setq gp (ssget))  (Command "change" gp "" "p" "C"))
(DEFUN C:CLW  (/ gp) (setq gp (ssget))  (Command "change" gp "" "p" "LW"))
(DEFUN C:CT  (/ gp) (setq gp (ssget))  (command "change" gp "" "P" "T"))
(DEFUN C:CLT (/ gp) (setq gp (ssget))  (command "change" gp "" "P" "LT"))
(DEFUN C:CE  (/ gp) (setq gp (ssget))  (command "change" gp "" "P" "E"))
(DEFUN C:CL  (/ gp) (setq gp (ssget))  (Command "change" gp "" "P" "LA"))
(DEFUN C:CS  (/ gp) (setq gp (ssget))  (Command "change" gp "" "P" "S"))
(DEFUN C:OUT  (/ gp) (setq gp (ssget))  (command "layer" gp "*" "o" "*" "u" "*" "t"))
(defun c:Q0  () (COMMAND "ZOOM" "0.00005X"))
(defun c:LA1  () (COMMAND "LAYER" "NEW" "LAYER1" "SET" "LAYER1" "C" "1" "LAYER1" ""))
(defun c:LA2  () (COMMAND "LAYER" "NEW" "LAYER2" "SET" "LAYER2" "C" "2" "LAYER2" ""))
(defun c:LA3  () (COMMAND "LAYER" "NEW" "LAYER3" "SET" "LAYER3" "C" "3" "LAYER3" ""))
(defun c:LA4  () (COMMAND "LAYER" "NEW" "LAYER4" "SET" "LAYER4" "C" "4" "LAYER4" ""))
(defun c:LA5  () (COMMAND "LAYER" "NEW" "LAYER5" "SET" "LAYER5" "C" "5" "LAYER5" ""))
(defun c:LA6  () (COMMAND "LAYER" "NEW" "LAYER6" "SET" "LAYER6" "C" "6" "LAYER6" ""))
(defun c:LA7  () (COMMAND "LAYER" "NEW" "LAYER7" "SET" "LAYER7" "C" "7" "LAYER7" ""))
(defun c:LA8  () (COMMAND "LAYER" "NEW" "LAYER8" "SET" "LAYER8" "C" "8" "LAYER8" ""))
(defun c:LA9  () (COMMAND "LAYER" "NEW" "LAYER9" "SET" "LAYER9" "C" "9" "LAYER9" ""))
(defun c:LA10  () (COMMAND "LAYER" "NEW" "LAYER10" "SET" "LAYER10" "C" "10" "LAYER10" ""))
(defun c:LA11  () (COMMAND "LAYER" "NEW" "LAYER11" "SET" "LAYER11" "C" "11" "LAYER11" ""))
(defun c:LA12  () (COMMAND "LAYER" "NEW" "LAYER12" "SET" "LAYER12" "C" "12" "LAYER12" ""))
(defun c:LA13  () (COMMAND "LAYER" "NEW" "LAYER13" "SET" "LAYER13" "C" "13" "LAYER13" ""))
(defun c:LA14  () (COMMAND "LAYER" "NEW" "LAYER14" "SET" "LAYER14" "C" "14" "LAYER14" ""))
(defun c:LA15  () (COMMAND "LAYER" "NEW" "LAYER15" "SET" "LAYER15" "C" "15" "LAYER15" ""))
(defun c:LA250  () (COMMAND "LAYER" "NEW" "LAYER250" "SET" "LAYER250" "C" "250" "LAYER250" ""))
(defun c:LA251  () (COMMAND "LAYER" "NEW" "LAYER251" "SET" "LAYER251" "C" "251" "LAYER251" ""))
(defun c:LA252  () (COMMAND "LAYER" "NEW" "LAYER252" "SET" "LAYER252" "C" "252" "LAYER252" ""))
(defun c:LA253  () (COMMAND "LAYER" "NEW" "LAYER253" "SET" "LAYER253" "C" "253" "LAYER253" ""))
(defun c:LA254  () (COMMAND "LAYER" "NEW" "LAYER254" "SET" "LAYER254" "C" "254" "LAYER254" ""))
(defun c:LA255  () (COMMAND "LAYER" "NEW" "LAYER255" "SET" "LAYER255" "C" "255" "LAYER255" ""))
(defun c:LAM  () (COMMAND "_LAYMCH"))
(defun c:LAC  () (COMMAND "_LAYCUR"))
(defun c:LAI  () (COMMAND "_LAYISO"))
(defun c:LAUI  () (COMMAND "_LAYUNISO"))
(defun c:LACO  () (COMMAND "_COPYTOLAYER"))
(defun c:LAW  () (COMMAND "_LAYWALK"))
(defun c:LAF  () (COMMAND "_LAYFRZ"))
(defun c:LAO  () (COMMAND "_LAYOFF"))
(defun c:LAL  () (COMMAND "_LAYLCK"))
(defun c:LAUL  () (COMMAND "_LAYULK"))
(defun c:LAA  () (COMMAND "_LAYON"))
;(defun c:TF  () (COMMAND "textfit"))
;(defun c:TMSK  () (COMMAND "TEXTMASK"))
;(defun c:XT  () (COMMAND "TXTEXP"))
(defun c:AT  () (COMMAND "_ARCTEXT"))
(defun c:xh  () (COMMAND "_superhatch"))
;(defun c:bk  () (COMMAND "breakline"))
(defun c:q (/ sz ra pt)
  (SETQ AA (GETVAR "OSMODE"))
  (SETVAR "OSMODE" 45)
  (SETQ SZ 0.25)
  (SETQ RA 0.0)
  (SETQ pt (getpoint "\nWhich point? : "))
  (if (and (>= ra 0.0) (<= ra (* pi 0.5)))
    (setq ra ra)
  )
  (if (and (> ra (* pi 0.5)) (< ra pi))
    (setq ra (- ra (* pi 0.5)))
  )
  (if (and (>= ra pi) (<= ra (* pi 1.5)))
    (setq ra (- ra pi))
  )
  (if (and (> ra (* pi 1.5)) (< ra (* pi 2.0)))
    (setq ra (- ra (* pi 1.5)))
  )
  (if (>= ra (* pi 2.0))
    (setq ra 0.0)
  )
  (if pt
    (ELE1)
(PRINC)
  )
(SETVAR "OSMODE" AA)
)
(DEFUN ELE1 ()
(setq ip (getpoint "\nInsertion point : ")
      dx (- (car ip) (car pt))
      dy (- (cadr ip) (cadr pt))
      eg (strcat "DIST.= " (rtos (car pt) 2 3))
     ng (strcat "ELEV.= " (rtos (cadr pt) 2 3))
    ; eg (strcat "OFF. " (rtos (car pt) 2 4))
    ; ng (strcat "ELV. " (rtos (cadr pt) 2 4))
      ll (* (+ (max (strlen eg) (strlen ng)) 0.5) sz)
)
  
(if (and (>= dx 0.0) (>= dy 0.0))
    (setq la ra
          ta ra
          tx (+ (car ip) (* sz (- (cos ta) (* 0.3 (sin ta)))))
          ty (+ (cadr ip) (* sz (+ (* 0.3 (cos ta)) (sin ta))))))
(if (and (< dx 0.0) (> dy 0.0)) 
    (setq la (- pi ra)
          ta (- 0.0 ra)
        tx (+ (car ip) (* sz (- (cos ta) (* 0.3 (sin ta)))) (* ll (cos la)))
        ty (+ (cadr ip) (* sz (+ (* 0.3 (cos ta)) (sin ta))) (* ll (sin la)))))
(if (and (<= dx 0.0) (<= dy 0.0)) 
    (setq la (+ pi ra)
          ta ra
        tx (+ (car ip) (* sz (- (cos ta) (* 0.3 (sin ta)))) (* ll (cos la)))
        ty (+ (cadr ip) (* sz (+ (* 0.3 (cos ta)) (sin ta))) (* ll (sin la)))))
(if (and (> dx 0.0) (< dy 0.0)) 
    (setq la (- 0.0 ra)
          ta (- 0.0 ra)
          tx (+ (car ip) (* sz (- (cos ta) (* 0.3 (sin ta)))))
          ty (+ (cadr ip) (* sz (+ (* 0.3 (cos ta)) (sin ta))))))
(setq tp (list tx ty (caddr ip)))
;(COMMAND "STYLE" "ITALICC")
(SETVAR "CECOLOR" "3")
;(command "TEXT" "S" "ITALICC" tp sz (* ta (/ 180 pi)) ng "TEXT" "" eg)
(command "TEXT" tp sz (* ta (/ 180 pi)) ng "TEXT" "" eg)
(setq pt1x (list (+ (car ip) ll)(cadr ip)))
;(command "leader" pt ip pt1x "" "" "N" "" )
(command "leader" pt ip
	(strcat "@" (rtos ll) "<" (rtos (* la (/ 180 pi)))) "" " " "")

;(command "LINE" pt ip 
;(command "LINE" 
;      (strcat "@" (rtos ll) "<" (rtos (* la (/ 180 pi)))) "" "" )
;(setq pt (getpoint "\nWhich point : "))
;(SETVAR "OSMODE" AA)
       
)
(defun c:ve (/ sz ra pt)
  (SETQ AA (GETVAR "OSMODE"))
  (SETVAR "OSMODE" 45)
  (SETQ SZ 0.25)
  (SETQ RA 1.570796327)
  (SETQ pt (getpoint "\nWhich point? : "))
  (if (and (>= ra 0.0) (<= ra (* pi 0.5)))
    (setq ra ra)
  )
  (if (and (> ra (* pi 0.5)) (< ra pi))
    (setq ra RA)
  )
  (if (and (>= ra pi) (<= ra (* pi 1.5)))
    (setq ra RA)
  )
  (if (and (> ra (* pi 1.5)) (< ra (* pi 2.0)))
    (setq ra RA)
  )
  (if (>= ra (* pi 2.0))
    (setq ra RA)
  )
  (if pt
    (VELE1)
(PRINC)
  )
(SETVAR "OSMODE" AA)
)
(DEFUN VELE1 ()
(setq ip (getpoint "\nInsertion point : ")
      dx (- (car ip) (car pt))
      dy (- (cadr ip) (cadr pt))
      eg (strcat "DIST.= " (rtos (car pt) 2 3))
     ng (strcat "ELEV.= " (rtos (cadr pt) 2 3))
    ; eg (strcat "OFF. " (rtos (car pt) 2 4))
    ; ng (strcat "ELV. " (rtos (cadr pt) 2 4))
      ll (* (+ (max (strlen eg) (strlen ng)) 0.5) sz)
)
  
(if (and (>= dx 0.0) (>= dy 0.0))
    (setq la ra
          ta ra
          tx (+ (car ip) (* sz (- (cos ta) (* 0.3 (sin ta)))))
          ty (+ (cadr ip) (* sz (+ (* 0.3 (cos ta)) (sin ta))))))
(if (and (< dx 0.0) (> dy 0.0)) 
    (setq la (- pi ra)
          ta (- 0.0 ra)
        tx (+ (car ip) (* sz (- (cos ta) (* 0.3 (sin ta)))) (* ll (cos la)))
        ty (+ (cadr ip) (* sz (+ (* 0.3 (cos ta)) (sin ta))) (* ll (sin la)))))
(if (and (<= dx 0.0) (<= dy 0.0)) 
    (setq la (+ pi ra)
          ta ra
        tx (+ (car ip) (* sz (- (cos ta) (* 0.3 (sin ta)))) (* ll (cos la)))
        ty (+ (cadr ip) (* sz (+ (* 0.3 (cos ta)) (sin ta))) (* ll (sin la)))))
(if (and (> dx 0.0) (< dy 0.0)) 
    (setq la (- 0.0 ra)
          ta (- 0.0 ra)
          tx (+ (car ip) (* sz (- (cos ta) (* 0.3 (sin ta)))))
          ty (+ (cadr ip) (* sz (+ (* 0.3 (cos ta)) (sin ta))))))
(setq tp (list tx ty (caddr ip)))
;(COMMAND "STYLE" "ITALICC")
(SETVAR "CECOLOR" "2")
;(command "TEXT" "S" "ITALICC" tp sz (* ta (/ 180 pi)) ng "TEXT" "" eg)
(command "TEXT" tp sz (* ta (/ 180 pi)) ng "TEXT" "" eg)
(setq pt1x (list (+ (car ip) ll)(cadr ip)))
;(command "leader" pt ip pt1x "" "" "N" "" )
(command "LINE" pt ip
	(strcat "@" (rtos ll) "<" (rtos (* la (/ 180 pi)))) "" " " "")

;(command "LINE" pt ip 
;(command "LINE" 
;      (strcat "@" (rtos ll) "<" (rtos (* la (/ 180 pi)))) "" "" )
;(setq pt (getpoint "\nWhich point : "))
;(SETVAR "OSMODE" AA)
       
)
(defun c:ne (/ sz ra pt)
  (SETQ AA (GETVAR "OSMODE"))
  (SETVAR "OSMODE" 45)
  (SETQ SZ 0.25)
  (SETQ RA 0.0)
  (SETQ pt (getpoint "\nWhich point? : "))
  (if (and (>= ra 0.0) (<= ra (* pi 0.5)))
    (setq ra ra)
  )
  (if (and (> ra (* pi 0.5)) (< ra pi))
    (setq ra (- ra (* pi 0.5)))
  )
  (if (and (>= ra pi) (<= ra (* pi 1.5)))
    (setq ra (- ra pi))
  )
  (if (and (> ra (* pi 1.5)) (< ra (* pi 2.0)))
    (setq ra (- ra (* pi 1.5)))
  )
  (if (>= ra (* pi 2.0))
    (setq ra 0.0)
  )
  (if pt
    (NE1)
(PRINC)
  )
(SETVAR "OSMODE" AA)
)
(DEFUN NE1 ()
(setq ip (getpoint "\nInsertion point : ")
      dx (- (car ip) (car pt))
      dy (- (cadr ip) (cadr pt))
      eg (strcat "E. " (rtos (car pt) 2 3))
     ng (strcat "N. " (rtos (cadr pt) 2 3))
    ; eg (strcat "OFF. " (rtos (car pt) 2 4))
    ; ng (strcat "ELV. " (rtos (cadr pt) 2 4))
      ll (* (+ (max (strlen eg) (strlen ng)) 0.5) sz)
)
  
(if (and (>= dx 0.0) (>= dy 0.0))
    (setq la ra
          ta ra
          tx (+ (car ip) (* sz (- (cos ta) (* 0.3 (sin ta)))))
          ty (+ (cadr ip) (* sz (+ (* 0.3 (cos ta)) (sin ta))))))
(if (and (< dx 0.0) (> dy 0.0)) 
    (setq la (- pi ra)
          ta (- 0.0 ra)
        tx (+ (car ip) (* sz (- (cos ta) (* 0.3 (sin ta)))) (* ll (cos la)))
        ty (+ (cadr ip) (* sz (+ (* 0.3 (cos ta)) (sin ta))) (* ll (sin la)))))
(if (and (<= dx 0.0) (<= dy 0.0)) 
    (setq la (+ pi ra)
          ta ra
        tx (+ (car ip) (* sz (- (cos ta) (* 0.3 (sin ta)))) (* ll (cos la)))
        ty (+ (cadr ip) (* sz (+ (* 0.3 (cos ta)) (sin ta))) (* ll (sin la)))))
(if (and (> dx 0.0) (< dy 0.0)) 
    (setq la (- 0.0 ra)
          ta (- 0.0 ra)
          tx (+ (car ip) (* sz (- (cos ta) (* 0.3 (sin ta)))))
          ty (+ (cadr ip) (* sz (+ (* 0.3 (cos ta)) (sin ta))))))
(setq tp (list tx ty (caddr ip)))
;(COMMAND "STYLE" "ITALICC")
(SETVAR "CECOLOR" "3")
;(command "TEXT" "S" "ITALICC" tp sz (* ta (/ 180 pi)) ng "TEXT" "" eg)
(command "TEXT" tp sz (* ta (/ 180 pi)) ng "TEXT" "" eg)
(setq pt1x (list (+ (car ip) ll)(cadr ip)))
;(command "leader" pt ip pt1x "" "" "N" "" )
(command "leader" pt ip
	(strcat "@" (rtos ll) "<" (rtos (* la (/ 180 pi)))) "" " " "")

;(command "LINE" pt ip 
;(command "LINE" 
;      (strcat "@" (rtos ll) "<" (rtos (* la (/ 180 pi)))) "" "" )
;(setq pt (getpoint "\nWhich point : "))
;(SETVAR "OSMODE" AA)
       
)

;------------------------------------------------------------------------------------

(defun c:idtab()
       (setq h (getdist "\nEnter height of text:"))
       (setq ha (getangle "\nEnter two point to show the Horizontal angle:"))
       (setq va (getangle "\nEnter two point to show the vertical angle:"))
       (setq ds1 (getdist "\nEnter width of 1st colum:"))
       (setq ds2 (getdist "\nEnter width of 2nd colum:"))
       (setq ds3 (getdist "\nEnter height of Row:"))
       (setq bs (getpoint "\nEnter Base point:"))
       (setq b (getpoint "\nEnter start point:"))
       (setq lm 0)
       (setq bs1 (polar bs ha ds1))
       (setq bs2 (polar bs ha (+ ds1 ds2)))
       (command "layer" "n" "table" "c" "7" "table" "")
       (command "layer" "s" "table" "")
       (command "units" 2 3 2 4 0 N)

  (while b
       (SETQ KK (POLAR B (+ VA PI) H))
       (setq st (polar bs va (* ds3 lm)))
       (setq st1 (polar bs1 va (* ds3 lm)))
       (setq st2 (polar bs2 va (* ds3 lm)))
       (COMMAND "TEXT" KK H (RTD HA) (+ 1 LM))
       (command "text" st h (rtd ha) (+ 1 LM))
       (command "text" st1 h (rtd ha) (rtos (car b)))
       (command "text" st2 h (rtd ha) (rtos (cadr b))) 
       (setq lm (+ lm 1))
       (setq b (getpoint "\nEnter next point:"))
       )   
  )     
;khallasa!!!
