(DEFUN C:TCOR()
(command "osnap" "none")
(setq i (open "tcor.cor" "w"))
(prompt "...        Select Your Point Please      ...")
(setq ent1 (ssget '((0 . "point"))))
(setq num (sslength ent1))
(setq av (getreal"\nInterval Between lines:"))
(setq cnum (getint"\nNumber Of Columns:"))
(setq dist (getreal"\nDistance Between Pt#,X,Y:"))
(setq pcl (/ num cnum))
(setq p1 (getpoint"\nSelect Start Positoin:"))
(setq txt (getreal"\nEnter Text High:"))
(setq cnt 0)
(repeat num
(setq s1 (ssname ent1 cnt))
(setq s2 (entget s1))
(setq pnt (cdr (assoc 10 s2)))
(setq x (car pnt))
(setq x (rtos x 2 2))
(setq y (cadr pnt))
(setq y (rtos y 2 2))
(setq p2 (polar pnt 2.4 av))
(if (= cnt pcl) (setq p1 (getpoint"\nSelect New Position:")))
(if (= cnt (* 2 pcl)) (setq p1 (getpoint"\nSelect New Position:")))
(if (= cnt (* 3 pcl)) (setq p1 (getpoint"\nSelect New Position:")))
(if (= cnt (* 4 pcl)) (setq p1 (getpoint"\nSelect New Position:")))
(setq cnt (1+ cnt))
(princ cnt i)
(princ "," i)
(princ x i)
(princ "," i)
(princ y i)
(princ "\n" i)
(command "text" "m" p2 txt 0 cnt)
(setq xp (polar p1 0 dist))
(setq yp (polar p1 0 (* 2.5 dist)))
(command "text" "m" p1 txt 0 cnt)
(command "text" "m" xp txt 0 x)
(command "text" "m" yp txt 0 y)
(setq p1 (polar p1 4.7124 5.0))
)
)
