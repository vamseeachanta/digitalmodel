;this program allow you to draw a square net, you have a choice to define length of square and
;first corner and second corner if you choose corners by mouse you must choose point with
;integer coordinates the square will be drawen and coordinates text will be placed along the
;frame with suitable scale as you know length of square when printing will be 10cm for topogaphic
;drwaings that mean it is beter for you if you know scale of printing befor making the net incase
;not to change scale of coordinates text.
;load the program then enter mnet at command line
;best regards
(defun c:mnet (/ p1 p2 d l w nx ny p3 p4 i k)
(setq obm (getvar "blipmode")) 
(setq oom (getvar "osmode"))
(setq andr(getvar"angdir"))
(setvar "angdir"1)
(setq andb(getvar"angbase")) 
(setvar "angbase"(/ pi 2))
(setq aunt(getvar"aunits"))  
(setvar "aunits"2)
(setvar "dimaunit"2)
(setvar"dimadec"4)
(setq p1 (getpoint "\n enter upper left corner"))
(setq p2 (getcorner p1"\n enter other corner"))
(setq d (getdist "\n enter length of square "))
(setq l (abs(-(car p2)(car p1))))
(setq w (abs(-(cadr p1)(cadr p2))))
(setq nx (/ l d))
(setq ny (/ w d))
(setq nx1 (fix nx))
(setq ny1 (fix ny))
(setq p3 (list (car p1)(cadr p2)))
(setq p4 (list(car p2)(cadr p1)))
(setq p5 (list(+(car p1)(* nx1 d))(cadr p1)))
(setq p6 (list(car p1)(-(cadr p1)(* ny1 d))))
(setq sfa (* 0.025 d))
(setq i 0)
(while(<= i nx1)
  (setvar "osmode"0)
  (command "line" (list(+(car p1)(* i d))(cadr p1))(list(+(car p1)(* i d))(cadr p6)) "")
  
  (setq pnx (list(+(car p1)(* i d))(cadr p1)))
  (setq pnx1 (list(+(car pnx)(* 0.01 d))(-(cadr pnx)(* 0.01 d))))
  (command "text" pnx1 sfa 200 (rtos(car pnx)2 0))
  (setq i (+ 1 i))
  )
(setq k 0)
(while(<= k ny1)
  (command "line" (list(car p1)(-(cadr p1)(* k d)))(list(car p5)(-(cadr p5)(* k d)))"")
  
  (setq pny (list(car p1)(-(cadr p1)(* k d))))
  (setq pny1 (list(+(car pny)(* 0.01 d))(+(cadr pny)(* 0.01 d))))
  (command "text" pny1 sfa 100 (rtos(cadr pny)2 0))
  (setq k (+ 1 k))
  )
  (setvar"angbase"andb)
  (setvar "angdir"andr)
  (setvar"aunits"aunt) 
  (setvar "osmode"oom)
)
