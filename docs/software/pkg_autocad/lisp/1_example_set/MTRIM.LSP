(Defun C:TT ()
  (Setq CVAR (Getvar "CMDECHO"))
  (Setvar "CMDECHO" 0)
  (Prompt "Select cutting edges")
  (Setq CUTEDG (Ssget))
  (Prompt "Select objects to trim")
  (Setq SS (SSget))
  (Setq LEN (SSlength SS))
  
  (Setq I -1)
  (Setq SIDE (getpoint"pick side to trim"))
  (Command "TRIM" CUTEDG "")
  (Repeat LEN
   (Setq I (1+ I))
   (Command (List(SSname SS I) SIDE))
  )
  (Command "")
  (Setvar "CMDECHO" CVAR)
  (Princ "\nTrim complete.")
  (Princ)
)
