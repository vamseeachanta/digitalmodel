**********************// side slope value //
(princ "\n command reference  for slope value: slope \n command reference  for superelevation value: selev")
(defun C:slope ()
(setvar "OSMODE" 35)
(setq sl1 (getpoint "\n <pravin> Select the first point on the slpoe: "))
(setq sl2 (getpoint "\n <pravin> Select the next point on the slpoe: "))
(setq sl1x (car sl1))
(setq sl1y (cadr sl1))
(setq sl2x (car sl2))
(setq sl2y (cadr sl2))
(setq slopl (abs (/ (- sl1x sl2x) (- sl1y sl2y))))
(setq slopl (strcat (rtos slopl 2 1) "H : 1V"))
(setvar "OSMODE" 0)
(setq texl (getpoint "\n <pravin> Specify text insertion point: "))
(setq texangl (* (/ 180 pi) (atan (/ (- sl1y sl2y) (- sl1x sl2x)))))
(command "style" "arial" "arial.ttf" 0 "" "" "" "" "")
(command "text" "s" "arial" "c" texl 1.0 texangl slopl)
(command "osmode" 35)
(princ))

******************************// superelevation value //
(defun C:slope ()
(setvar "OSMODE" 35)
(setq sel1 (getpoint "\n <pravin> Select the first point: "))
(setq sel2 (getpoint "\n <pravin> Select the next point: "))
(setq sel1x (car sel1))
(setq sel1y (cadr sel1))
(setq sel2x (car sel2))
(setq sel2y (cadr sel2))
(setq supl (* 100 (abs (/ (- sel1y sel2y) (- sel1x sel2x)))))
(setq supl (strcat (rtos supl 2 2) "%"))
(setvar "OSMODE" 0)
(setq txl (getpoint "\n <pravin> Specify text insertion point: "))
(setq txangl (* (/ 180 pi) (atan (/ (- sel1y sel2y) (- sel1x sel2x)))))
(command "style" "arial" "arial.ttf" 0 "" "" "" "" "")
(command "text" "s" "arial" "c" txl 1.0 txangl supl)
(setq const (* (/ (abs (- sel1x sel2x)) (- sel1x sel2x)) (/ (abs (- sel1y sel2y)) (- sel1y sel2y))))
(command "leader" (list 0 0) (list (* const 2.2) 0) "" "" "n")
(setq leaxy (list (car txl) (- (cadr txl) 0.2)))
(command "move" "l" "" (list (* const 1.1) 0) leaxy)
(command "rotate" "l" "" leaxy txangl)
(command "osmode" 35)
(princ))
*****************************
