(defun c:v () (command "zoom" "p" ""))
(defun c:zz () (command "zoom" "d"))
(defun c:z2 () (command "zoom" "0.2x"))
(defun c:c () (ssget) (command "copy" "p" "" "m"))
(defun c:hi () (ssget) (command "change" "p" "" "p" "lt" "hidden" ""))
(defun c:co () (ssget) (command "change" "p" "" "p" "lt" "continuous" ""))
(defun c:ce () (ssget) (command "change" "p" "" "p" "lt" "center" ""))
(defun c:0 () (ssget) (command "change" "p" "" "p" "c" "bylayer" ""))
(defun c:1 () (ssget) (command "change" "p" "" "p" "c" "1" ""))
(defun c:2 () (ssget) (command "change" "p" "" "p" "c" "2" ""))
(defun c:3 () (ssget) (command "change" "p" "" "p" "c" "3" ""))
(defun c:4 () (ssget) (command "change" "p" "" "p" "c" "4" ""))
(defun c:5 () (ssget) (command "change" "p" "" "p" "c" "5" ""))
(defun c:6 () (ssget) (command "change" "p" "" "p" "c" "6" ""))
(defun c:7 () (ssget) (command "change" "p" "" "p" "c" "7" ""))
(defun c:8 () (ssget) (command "change" "p" "" "p" "c" "8" ""))
(defun c:30 () (ssget) (command "rotate" "p" "" pause "30"))
(defun c:-30 () (ssget) (command "rotate" "p" "" pause "-30"))
(defun c:45 () (ssget) (command "rotate" "p" "" pause "45"))
(defun c:60 () (ssget) (command "rotate" "p" "" pause "60"))
(defun c:-60 () (ssget) (command "rotate" "p" "" pause "-60"))
(defun c:90 () (ssget) (command "rotate" "p" "" pause "90"))
(defun c:180 () (ssget) (command "rotate" "p" "" pause "180"))
(defun c:-45 () (ssget) (command "rotate" "p" "" pause "-45"))
(defun c:-90 () (ssget) (command "rotate" "p" "" pause "-90"))
(defun c:dh () (command "dim1" "hor" pause))
(defun c:dc () (command "dim1" "con" pause))
(defun c:dv () (command "dim1" "ver" pause))
(defun c:da () (command "dim1" "ali" pause))
(defun c:df () (command "dim1" "new"))
(defun c:du () (command "dim1" "up"))
(defun c:mp (/ list23 lri23 mpn23 lay23 lt23 col23)
  (prompt "\nSelect objects: ")
  (setvar "cmdecho" 0)
  (command "select" "au" pause)
  (setq list23 (ssget "p"))
  (setq lri23 (entsel "\nSelect entity: "))
  (command "undo" "mark")
  (setq mpn23 (entget (car lri23)))
  (setq lay23 (cdr(assoc 8 mpn23)))
  (setq lt23 (cdr(assoc 6 mpn23)))
  (setq col23 (cdr (assoc 62 mpn23)))
  (if (= lt23 nil) (setq lt23 "bylayer"))
  (if (= lt23 "byblock") (setq lt23 "byblock"))
  (if (= col23 nil) (setq col23 "bylayer"))
  (if (= col23 "byblock") (setq col23 "byblock"))
  (command "change" list23 "" "p" "la" lay23 "c" col23 "lt" lt23 "")
  (setvar "cmdecho" 1)
)
(defun c:lk (/ list23 lri23 mpn23 lay23 lt23 col23)
  (setq lri23 (entsel "\nSelect object: "))
  (setvar "cmdecho" 0)
  (command "undo" "mark")
  (setq mpn23 (entget (car lri23)))
  (setq lay23 (cdr(assoc 8 mpn23)))
  (command "layer" "s" lay23 "")
  (setvar "cmdecho" 1)
)
(defun c:ml (/ list13 lri13 mpn13 lay13)
  (prompt "\nSelect objects: ")
  (setvar "cmdecho" 0)
  (command "select" "au" pause)
  (setq list13 (ssget "p"))
  (setq lri13 (entsel "\nSelect entity to match: "))
  (command "undo" "mark")
  (setq mpn13 (entget (car lri13)))
  (setq lay13 (cdr (assoc 8 mpn13)))
  (command "change" list13 "" "p" "la" lay13 "")
  (princ)
  (setvar "cmdecho" 1)
)

(defun c:chh (/ eni23 n23 ht23 l23 e23)
  (initget 7)
  (prompt "\nSelect texts: ")
  (setvar "cmdecho" 0)
  (command "select" "au" pause)
  (setq eni23 (ssget "p"))
  (setq n23 (sslength eni23))
  (setq ht23 (getdist "\nNew height: "))
  (setq l23 0)
  (command "undo" "mark")
      (while (< l23 n23)
        (setq e23 (entget (ssname eni23 l23)))
        (if (= "TEXT" (cdr (assoc 0 e23)))
          (progn
            (setq e23 (subst (cons 40 ht23) (assoc 40 e23) e23))
            (entmod e23)
          )
        )
        (setq l23 (1+ l23))
      )
  (prompt "\nFinished.")
  (setvar "cmdecho" 1)
)
(defun c:cw (/ ennyi23 wb23 shell23 loui23 el23)
 (initget 7)
 (prompt "\nSelect texts: ")
  (command "select" "au" pause)
  (setq ennyi23 (ssget "p"))
  (setvar "cmdecho" 0)
  (initget 7)
  (setq wb23 (getdist "\nNew width: "))
  (setq shell23 (sslength ennyi23))
  (command "undo" "mark")
  (setq loui23 0)
      (while (< loui23 shell23)
        (setq el23 (entget (ssname ennyi23 loui23)))
        (if (= "TEXT" (cdr (assoc 0 el23)))
          (progn
            (setq el23 (subst (cons 41 wb23) (assoc 41 el23) el23))
            (entmod el23)
          )
        )
        (setq loui23 (1+ loui23))
      )
  (setvar "cmdecho" 1)
)

(DEFUN C:XX ()
 (SETQ CMD (GETVAR "CMDECHO"))
 (SETVAR "CMDECHO" 0)
 (COMMAND "UCS" "W")
 (SETVAR "CMDECHO" 1)
 (PROMPT"\nHay chon duong kich thuoc VER...")
 (SETQ SET (SSGET))
 (PROMPT"\nHay chon duong giong moi")
 (SETQ P1 (GETPOINT))
 (SETQ X3 (CAR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L13 (ASSOC 13 A))
     (SETQ M13 (CDR L13))
     (SETQ L14 (ASSOC 14 A))
     (SETQ M14 (CDR L14))
     (SETQ P13 (LIST 13 X3 (CADR M13) (CADDR M13)))
     (SETQ P14 (LIST 14 X3 (CADR M14) (CADDR M14)))
     (SETQ A (SUBST P13 L13 A))
     (SETQ A (SUBST P14 L14 A))
     (ENTMOD A)                 
    )
   )
  (SETQ INDEX (+ INDEX 1))
 )
 (SETVAR "CMDECHO" 0)
 (COMMAND "UCS" "P")
 (SETVAR "CMDECHO" CMD)
 (PRINC)
)

(DEFUN C:YY ()
 (SETQ CMD (GETVAR "CMDECHO"))
 (SETVAR "CMDECHO" 0)
 (COMMAND "UCS" "W")
 (SETVAR "CMDECHO" 1)
 (PROMPT"\nHay chon duong kich thuoc HOR...")
 (SETQ SET (SSGET))
 (PROMPT"\nHay chon duong giong moi")
 (SETQ P1 (GETPOINT))
 (SETQ Y3 (CADR P1))
 (SETQ QUANT (SSLENGTH SET))
 (SETQ INDEX 0)
  (WHILE (< INDEX QUANT)
   (IF (AND(= "DIMENSION" (CDR (ASSOC 0 (SETQ A (ENTGET (SSNAME SET INDEX))))))
       )
    (PROGN
     (SETQ L13 (ASSOC 13 A))
     (SETQ M13 (CDR L13))
     (SETQ L14 (ASSOC 14 A))
     (SETQ M14 (CDR L14))
     (SETQ P13 (LIST 13 (CAR M13) Y3 (CADDR M13)))
     (SETQ T13 (CDR P13))
     (SETQ P14 (LIST 14 (CAR M14) Y3 (CADDR M14)))
     (SETQ A (SUBST P13 L13 A))
     (SETQ A (SUBST P14 L14 A))
     (ENTMOD A)                 
    )
   )
  (SETQ INDEX (+ INDEX 1))
 )
 (SETVAR "CMDECHO" 0)
 (COMMAND "UCS" "P")
 (SETVAR "CMDECHO" CMD)
)

(defun C:Ct ()
(setq v (getvar "osmode"))
(setq pt1 (getpoint "First point : "))
(setq pt2 (getpoint "End point : " pt1))
(command "osnap" "none")
(setq goc (angle pt1 pt2))
(setq kcach (distance pt1 pt2))
(setq pt3 (polar pt1 goc (* 2 (/ kcach 5))))
(setq pt4 (polar pt1 goc (* 3 (/ kcach 5))))
(setq pt5 (polar pt3 (+ (/ PI 2) goc) (* kcach 0.25)))
(setq pt6 (polar pt4 (+ (/ PI 2) goc) (* kcach -0.25)))
(command "pline" pt1 pt3 pt5 pt6 pt4 pt2 "")
(setvar "osmode" v )
)
(load "c:/progra)
