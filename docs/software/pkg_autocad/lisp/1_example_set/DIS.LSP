(DEFUN C:DH()
(defun *error* (msg)
	(princ "error: ")
	(princ msg)
	(terpri)
)
	(COMMAND "COLOR" "bylayer")
	(command "LAYER" "THAW" "0" "")
	(command "LAYER" "SET" "0" "c" 4 "" "")
	(command "osnap" "node")
	(WHILE (SETQ SP (GETPOINT "\nSELECT FIRST POINT"))
		(SETQ EP (GETPOINT "\nSELECT SECOND POINT"))
		(SETQ DS (DISTANCE SP EP))
		(SETQ ANG (ANGLE SP EP))
		(SETQ D2 (/ DS 2))
		(setq pi2 (/ pi 2))
		(SETQ M2 (POLAR SP ANG D2))
		(setq ang1 (+ ang pi2))
		(SETQ M3 (POLAR m2 ANG1 5.5))
		(SETQ DS (RTOS DS 1 2))
		(setq deg (/ (* ang 180) pi))
		(COMMAND "TEXT" "m" M3 5 deg DS)
	)
)
