THANG HAI CANH 3D
-----------------------------------------------------------------------------------------------

(defun NHT ()
    (setq sbut (getint "chieu sau buong thang : "))
    (setq rbut (getint "chieu rong buong thang : "))
    (setq catg (getint "chieu cao tang : "))
    (setq rchn (getint " chieu rong chieu nghi : "))
    (setq rcat (getint "chieu rong canh thang : "))
    (setq sbac (getint "so bac tren mot canh : "))
    (setq st (getint "so tang thang: "))
    (setq P0 (getpoint "cho goc buong thang : "))
 )
(defun SLTD ()
    (setq caba (/ (/ catg 2) (+ sbac 1)))
    (setq roba (/ (- sbut rchn) sbac))
    (setq cdam (/ rbut 8))
    (setq rdam (/ rbut 14))
    (setq P1 (polar P0 0 rchn))
    (setq P2 (polar P1 (/ pi 2) (- rbut rcat)))
    (setq P3 (polar P1 pi rdam))
    (setq P4 (polar P1 (/ pi 2) rcat))
    (setq P5 (polar P4 0 (- sbut rchn)))
    (setq P6 (polar P5 (/ pi 2) (- rbut rcat)))
    (setq cot1 (- (/ catg 2) caba))
    (setq cot2 (+ (/ catg 2) caba))
    (setq C0 (list (car P1) (cadr P1) (/ catg 2)))
 )
(defun C1TD ()
    (command "BOX" P1 "L" roba rchn cot1)
    (setq P11 (polar P1 0 roba))
    (setq P11 P1)
    (setq cot11 (- cot1 caba))       
    (while (< (distance P1 P11) (- sbut (+ rchn (+ roba (/ roba 2)))))
           (setq P11 (polar P11 0 roba))
           (command "BOX" P11 "L" roba rcat cot11)
           (setq cot11 (- cot11 caba))     		
    )
    (setq ss1 (ssget "W" P1 P5))
    (setq C1 (list (car P1) (cadr P1) (- (/ catg 2) cdam)))
    (setq C2 (list (car P1) (+ (cadr P1) rcat) (- (/ catg 2) cdam)))
    (setq be (/ (* (- (/ catg 2) cdam) (- sbut rchn)) (- (/ catg 2) caba)))
    (setq C3 (polar P1 0 be))
    (command "SLICE" ss1 "" C1 C2 C3 C0) (setq ss1 nil) 
 )
(defun C2TD ()
    (command "BOX" P2 "L" roba rchn cot2)
    (setq P22 (polar P2 0 roba))
    (setq P22 P2)
    (setq cot22 (+ cot2 caba))
    (while (< (distance P2 P22) (- sbut (+ rchn (+ roba (/ roba 2)))))
           (setq P22 (polar P22 0 roba))
           (command "BOX" P22 "L" roba rcat cot22)
           (setq cot22 (+ cot22 caba))
    )
    (setq ss2 (ssget "W" P2 P6))
    (setq CC1 (list (car P2) (cadr P2) (+ (- (/ catg 2) cdam) caba)))
    (setq CC2 (list (car P2) (+ (cadr P2) rcat) (+ (- (/ catg 2) cdam ) caba)))
    (setq hbe (* 2 (+ (- (/ catg 2) cdam) (/ caba 2))))
    (setq CC3 (list (car C3) (cadr C3) hbe))
    (command "SLICE" ss2 "" CC1 CC2 CC3 C0) (setq ss2 nil)
 )
(defun CNTD ()
    (command "BOX" P0 "L" rchn rbut 100)
    (setq ss3 (ssget "L"))
    (command "MOVE" ss3 "" P0 (list (car P0) (cadr P0) (- (/ catg 2) 100)))
    (setq ss3 nil)
    (command "BOX" P3 "L" rdam rbut cdam)
    (setq ss4 (ssget "L"))
    (command "MOVE" ss4 "" P3 (list (car P3) (cadr P3) (- (/ catg 2) cdam)))
    (setq ss4 nil)
 )
(defun VLCT ()
    (setq lc1 (polar P1 (/ pi 2) (- rchn 50)))
    (setq lccn (polar lc1 pi 50))
    (setq P7 (polar P2 (/ pi 2) 50))
    (setq P8 (list (car P7) (cadr P7) (+ catg 1000)))
    (setq t1lc1 (list (car lc1) (cadr lc1) (+ (/ catg 2) 900))
          t2lc1 (list (car P4) (cadr P4) (+ (/ catg 2) 900))
          t3lc1 (list (car P5) (cadr P5) (+ caba 900))
          d1lc1 (list (car lc1) (cadr lc1) (+ (/ catg 2) 600))
          d2lc1 (list (car P4) (cadr P4) (+ (/ catg 2) 600))
          d3lc1 (list (car P5) (cadr P5) (+ caba 600))
          tlccn (list (car lccn) (cadr lccn) (+ (/ catg 2) 900))
          dlccn (list (car lccn) (cadr lccn) (+ (/ catg 2) 600))
          t1lc2 (list (car P2) (cadr P2) (+ (/ catg 2) (+ caba 900)))
          t2lc2 (list (car P7) (cadr P7) (+ (/ catg 2) (+ caba 900)))
          t3lc2 (list (car P5) (cadr P5) (+ catg 900))
          d1lc2 (list (car P2) (cadr P2) (+ (/ catg 2) (+ caba 600)))
          d2lc2 (list (car P7) (cadr P7) (+ (/ catg 2) (+ caba 600)))
          d3lc2 (list (car P5) (cadr P5) (+ catg 600))
      )
     (command "BOX" lc1 "L" (- sbut rchn) 50 (+ (/ catg 2) 900))
     (setq s1 (ssget "L")) 
     (command "SLICE" s1 "" t1lc1 t2lc1 t3lc1 P1) 
     (setq s2 (ssget "L"))
     (command "SLICE" s2 "" d1lc1 d2lc1 d3lc1 P8)
     (setq s1 nil s2 nil)
     (setq s12 (ssget "L"))
     (command "COPY" s12 "" P0 (list (car P0) (+ (- (cadr P0) rcat) 50) (caddr P0)) "")
     (setq s12 nil)
     (setq s13 (ssget "L"))
     (command "BOX" lccn "L" 50 (- (+ rbut 100) (* 2 rcat)) (+ (/ catg 2) 900))
     (setq s13 nil)
     (setq s3 (ssget "L"))
     (command "SLICE" s3 "" d1lc1 d2lc1 dlccn P8)
     (setq s3 nil)
     (setq s33 "L")
     (command "COPY" s33 "" tlccn (list (car t3lc2) (- (cadr t3lc2) 50) (caddr t3lc2)) "")
     (setq s33 nil)
     (command "BOX" (list (car P0) (cadr P0) (+ (/ catg 2) 600)) "L" rchn rbut 300)
     (setq scn (ssget "L"))
     (command "BOX" (list (+ (car P0) 50) (+ (cadr P0) 50) (+ (/ catg 2) 600)) "L" rchn (- rbut 100) 300)
     (setq scc (ssget "L"))
     (command "SUBTRACT" scn "" scc "")
     (setq scc nil scn nil)
     (command "BOX" P2 "L" (- sbut rchn) 50 (+ catg 900))
     (setq s4 (ssget "L"))
     (command "SLICE" s4 "" t1lc2 t2lc2 t3lc2 P1) (setq s4 nil)
     (setq s5 (ssget "L"))
     (command "SLICE" s5 "" d1lc2 d2lc2 d3lc2 P8) (setq s5 nil)
     (setq s45 (ssget "L"))
     (command "COPY" s45 "" P0 (list (car P0) (- (+ (cadr P0) rcat) 50) (caddr P0)) "")
 )
(defun C:THANG3D ()
    (NHT)
    (setvar "osmode" 0)
    (SLTD)
    (C1TD)
    (C2TD)
    (CNTD)
    (VLCT)
    (setq C 1)
    (setq sss (ssget "W" P0 (list (+ 50 (car P6)) (cadr P6))))
    (While (< C st)
           (command "COPY" sss "" "0,0,0" (append (list 0 0) (list (* C catg)))
           )
           (setq C (1+ C))
    )
    (setq P00 (list (+ (car P0) sbut) (+ (cadr P0) rbut)))
    (setq ssal (ssget "W" P0 P00))
    (command "UNION" ssal "")   
    (command "REDRAW")  
 )
