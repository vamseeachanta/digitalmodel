(command "style" "rsgv" "romans" "2" "1" "" "" "" "")
(defun c:increh()
(SETVAR "CECOLOR" "RED")
	(setvar "texteval" 0)
(setq pt(getpoint "\nPick point: "))
(setq xpt(car pt))
(setq ypt(cadr pt))
	(setq te_ins_pt (list (- xpt 1) (- ypt 7.5))
		val(car pt))
	(setq inc 10)
	(setq no_of_col 8)
	(setq di_of_col 10)
(repeat no_of_col
	(command "text" "c" te_ins_pt "90" (rtos val 2 0))
	(setq te_ins_pt(polar te_ins_pt 0 di_of_col)
		val (+ val inc)))
(C:CSX))
(DEFUN C:CSX()
(SETQ SX(SSGET "x" (LIST (CONS 7 "RSGV") (CONS 62 1))))
(SETQ PTT(LIST (CAR PT) (+ (CADR PT) 515)))
(COMMAND "COPY" SX "" PT PTT)
)
(defun c:increv()
(SETVAR "CECOLOR" "CYAN")
	(setvar "texteval" 0)
	(setq te_ins_pt (list (- xpt 7.5) (+ ypt 1))
		val(cadr pt))
	(setq inc 100)
	(setq no_of_row 6)
	(setq di_of_row 100)
(repeat no_of_row
	(command "text" "c" te_ins_pt "0" (rtos val 2 0))
	(setq te_ins_pt(polar te_ins_pt (/ pi 2) di_of_row)
		val (+ val inc)))
(C:CSY))
(DEFUN C:CSY()
(SETQ SY(SSGET "x" (LIST (CONS 7 "RSGV") (CONS 62 4))))
(SETQ PTY(LIST (+ (CAR PT) 715) (CADR PT)))
(COMMAND "COPY" SY "" PT PTY)
)
(defun c:gv()
(c:increv)(princ))
(defun c:gh()
(c:increh)(princ))
(defun c:gval()
(c:increh)
(c:increv)(princ))
