(defun c:TARGET (/ pt0 PT1 PT2 PT3 PT4 PT1A PT2A PT3A PT4A r1 R2)
  (setq r1 (getDIST "\nENTER THE RADIUS OF THE TARGET CIRCLE: "))
  (SETQ PT0 (GETPOINT "\nPICK THE CENTER OF THE TARGET CIRCLE: "))
  (SETQ R2 (/ R1 2))
  (SETQ PT1 (LIST (+ (CAR PT0) R2) (CADR PT0)))
  (SETQ PT1A (LIST (+ (CAR PT0) (* R1 1.5)) (CADR PT0)))
  (SETQ PT2 (LIST (- (CAR PT0) R2) (CADR PT0)))
  (SETQ PT2A (LIST (- (CAR PT0) (* R1 1.5)) (CADR PT0)))
  (SETQ PT3 (LIST (CAR PT0) (+ (CADR PT0) R2)))
  (SETQ PT3A (LIST (CAR PT0) (+ (CADR PT0) (* R1 1.5))))
  (SETQ PT4 (LIST (CAR PT0) (- (CADR PT0) R2)))
  (SETQ PT4A (LIST (CAR PT0) (- (CADR PT0) (* R1 1.5))))
  (COMMAND "CIRCLE" PT0 R1)
  (COMMAND "LINE"
    PT1A
    PT2A
    "")
  (COMMAND "LINE"
    PT3A
    PT4A
    "")
  (COMMAND "PLINE" PT1 "W" R1 "" "A" "A" 90 PT3 "")
  (COMMAND "PLINE" PT2 "W" R1 "" "A" "A" 90 PT4 "")
)
