Prepared By : Nguyen Huu Tuan
;**********************************************************************
(setvar "pickbox" 4)
(setvar "aperture" 4)
;ZOOM
(defun c:zp ()  (command "'.zoom" "p"))
(defun c:zw ()  (command "'.zoom" "w"))
(defun c:zz ()  (command "'.zoom" "p"))
(defun c:ze ()  (command "'.zoom" "e"))
(defun c:za ()  (command "'.zoom" "a"))
(defun c:zd ()  (command "'.zoom" "d"))
(defun c:+++ ()  (command "'.zoom" "0.1x"))
(defun c:++ ()  (command "zoom" "0.3x"))
(defun c:+ ()  (command "zoom" "0.5x"))
(defun c:- ()  (command "zoom" "2x"))
(defun c:-- ()  (command "zoom" "3x"))
(defun c:--- ()  (command "zoom" "4x"))
;PLINE
(defun c:pl () (command "pline"))
(defun c:pe () (command "pedit"))
(defun c:pa () (command "pline" pause "a"))
(defun c:pj () (command "pedit" pause "j"))
(defun c:pw () (command "pedit" pause "w"))
(defun c:lty () (command "linetype"))
(defun c:lts () (command "ltscale"))
(defun c:tri () (command "polygon" "3" pause "i"))
(defun c:trc () (command "polygon" "3" pause "c"))
(defun c:sqi () (command "polygon" "4" pause "i"))
(defun c:sqc () (command "polygon" "4" pause "c"))
;CHAMFER
(defun c:cf () (command "chamfer"))
(defun c:cfd () (command "chamfer" "d"))
(defun c:cf0 () (command "chamfer" "d" "0" ""))
;FILLET
(defun c:f () (command "fillet"))
(defun c:fr () (command "fillet" "r"))
(defun c:f0 () (command "fillet" "r" "0" ""))
;BREAK
(defun c:b () (command "break"))
(defun c:br () (command "break"))
(defun c:bf () (command "break" pause "f"))
;COPY
(defun c:c () (command "copy"))
(defun c:cp () (command "copy"))
(defun c:cm () (ssget) (command "copy" "p" "" "m"))
(defun c:dup () (ssget) (command "copy" "p" "" "0,0" "0,0"))
;ARRAY
(defun c:ar () (command "array"))
(defun c:arp () (ssget) (command "array" "p" "" "p"))
(defun c:arr () (ssget) (command "array" "p" "" "r"))
;TRIM
(defun c:t () (command "trim"))
(defun c:tr () (command "trim"))
(defun c:tf () (ssget) (command "trim" "p" "" "f"))
:EXTEND
(defun c:ee () (command "extend"))
(defun c:ef () (ssget) (command "extend" "p" "" "f"))
;DIM
(defun c:da () (command "dim1" "ali"))
(defun c:dl () (command "dim1" "lead" ))
(defun c:du () (command "dim1" "up" ))
(defun c:dv () (command "dim1" "ver" ))
(defun c:dn () (command "dim1" "new" ))
(defun c:dh () (command "dim1" "hor" ))
(defun c:dco () (command "dim1" "continue" ))
(defun c:das () (command "dim1" "dimasz" "0.10" "exit"))
;LAYER
(defun c:la () (command "layer"))
(defun c:ll () (command "ddlmodes"))
(defun c:lm () (command "layer" "m"))
(defun c:lt () (command "layer" "t"))
(defun c:lf () (command "layer" "f"))
(defun c:ln () (command "layer" "n"))
(defun c:lc () (command "layer" "c"))
(defun c:las () (command "layer" "t" pause "s" pause "f" pause ""))
(defun c:lof () (command "layer" "off"))
(defun c:lon () (command "layer" "on"))
;CHANGE
(defun c:ch () (command "change"))
(defun c:1 () (ssget) (command "change" "p" "" "p" "c" "1" ""))
(defun c:2 () (ssget) (command "change" "p" "" "p" "c" "2" ""))
(defun c:3 () (ssget) (command "change" "p" "" "p" "c" "3" ""))
(defun c:4 () (ssget) (command "change" "p" "" "p" "c" "4" ""))
(defun c:5 () (ssget) (command "change" "p" "" "p" "c" "5" ""))
(defun c:6 () (ssget) (command "change" "p" "" "p" "c" "6" ""))
(defun c:7 () (ssget) (command "change" "p" "" "p" "c" "7" ""))
(defun c:8 () (ssget) (command "change" "p" "" "p" "c" "8" ""))
(defun c:9 () (ssget) (command "change" "p" "" "p" "c" "9" ""))
(defun c:chth () (ssget) (command "change" "p" "" "p" "t"))
(defun c:che () (ssget) (command "change" "p" "" "p" "e"))
(defun c:byla () (command "color" "bylayer")(princ))
:BLOCK
(defun c:bl () (command "block"))
(defun c:i () (command "insert"))
(defun c:in () (command "insert"))
(defun c:inn () (command "insert" "" pause "" "" ""))
;SPACE
(defun c:ms () (command "mspace"))
(defun c:ps () (command "pspace"))
(defun c:tm () (command "tilemode"))
(defun c:tm0 () (command "tilemode" "0"))
(defun c:tm1 () (command "tilemode" "1"))
;TEXT
(defun c:dt () (command "dtext"))
(defun c:de () (command "ddedit"))
(defun c:st () (command "style"))
;ATTRIB
(defun c:ap () (command "attedit" "" "" "" "" pause "" "p"))
(defun c:as () (command "attedit" "" "" "" "" pause "" "s"))
(defun c:ah () (command "attedit" "" "" "" "" pause "" "h"))
(defun c:aa () (command "attedit" "" "" "" "" pause "" "a"))
(defun c:ast () (command "attedit" "" "" "" "" "auto" "" "s"))
(defun c:avc () (command "attedit" "" "" "" "" pause "" "v" "c"))
(defun c:avr () (command "attedit" "" "" "" "" pause "" "v" "r"))
;UCS
(defun c:uv () (command "ucs" "v"))
(defun c:us () (command "ucs" "s"))
(defun c:ur () (command "ucs" "r"))
(defun c:uw () (command "ucs" "w" "plan" ""))
(defun c:ux () (command "ucs" "x"))
(defun c:uy () (command "ucs" "y"))
(defun c:uz () (command "ucs" "z"))
(defun c:up () (command "ucs" "p"))
(defun c:ue () (command "ucs" "e"))
(defun c:u3 () (command "ucs" "3p" pause pause pause "plan" ""))
;OTHER
(defun c:c2 () (command "circle" "2p"))
(defun c:d () (command "dist"))
(defun c:do () (command "donut"))
(defun c:dw () (command "dview"))
(defun c:div () (command "divide"))
(defun c:ex () (command "explode"))
(defun c:ep () (command "explode"))
(defun c:el () (command "ellipse"))
(defun c:g () (command "grid"))
(defun c:hi () (command "hide"))
(defun c:lim () (command "limits"))
(defun c:li () (command "list"))
(defun c:m () (command "move"))
(defun c:me () (command "measure"))
(defun c:mm () (command "mirror"))
(defun c:mr () (command "mirror"))
(defun c:mi () (command "mirror"))
(defun c:nc () (command "shell" "nc"))
(defun c:o () (command "offset"))
(defun c:po () (command "polygon"))
(defun c:ro () (command "rotate"))
(defun c:rr () (command "rotate"))
(defun c:rt () (command "rotate"))
(defun c:s () (command "stretch" "c"))
(defun c:s1 () (command "surftab1"))
(defun c:s2 () (command "surftab2"))
(defun c:se () (command "select"))
(defun c:sd () (command "solid"))
(defun c:so () (command "solid"))
(defun c:ss () (command "scale"))
(defun c:sc () (command "scale"))
(defun c:sn () (command "snap"))
(defun c:v () (command "view"))
;MODIFY
(defun c:dr () (command "ddrmodes"))
(defun c:em () (command "ddemodes"))

;********************

(defun c:ls (/ ee23 xx23)
   (setvar "cmdecho" 0)
   (setq ee23 (car (entsel "\nPick Object on desired layer: ")))
   (if ee23 (progn
             (setq ee23 (entget ee23))
             (setq xx23 (cdr (assoc 8 ee23)))
             (command "layer" "s" xx23 "")
          )
    )
   (prompt (strcat "\nCurrent layer is now..." xx23))
   (setvar "cmdecho" 1)
   (princ)
)

;********************

(defun c:lf (/ ee23 xx23)
   (setvar "cmdecho" 0)
   (setq ee23 (car (entsel "\nPick Object on desired layer: ")))
   (if ee23 (progn
             (setq ee23 (entget ee23))
             (setq xx23 (cdr (assoc 8 ee23)))
             (command "layer" "f" xx23 "")
          )
    )
   (prompt (strcat  xx23 "\n is now freezed."))
   (setvar "cmdecho" 1)
   (princ)
)

;*********************

(defun c:tl (/ lou43)
   (setvar "cmdecho" 0)
   (setq lou43 (getstring "\nType layer name: "))
   (command "undo" "mark")
   (command "layer" "s" lou43 "")
   (prompt (strcat "\nCurrent layer is now..." lou43))
   (setvar "cmdecho" 1)
   (princ)
)

;*********************

(defun c:cl (/ mpn43 lri44)
    (prompt "\nSelect objects: ")
    (setvar "cmdecho" 0)
    (command "select" "au" pause)
    (setq mpn43 (ssget "p"))
    (setq lri44 (getstring "\nType desired linetype for entiti(es): "))
    (prompt "\nChanging linetype for entiti(es)... stand by.")
    (command "undo" "mark")
    (command "change" mpn43 "" "p" "lt" lri44 "")
    (prompt "\nFinished.")
    (setvar "cmdecho" 1)
    (princ)
)

;*********************

(defun c:mp (/ list23 lri23 mpn23 lay23 lt23 col23)
  (prompt "\nSelect objects: ")
  (setvar "cmdecho" 0)
  (command "select" "au" pause)
  (setq list23 (ssget "p"))
  (setq lri23 (entsel "\nSelect entity to match: "))
  (prompt "\nChanging entiti(es) properti(es)... stand by.")
  (command "undo" "mark")
  (setq mpn23 (entget (car lri23)))
  (setq lay23 (cdr(assoc 8 mpn23)))
  (setq lt23 (cdr(assoc 6 mpn23)))
  (setq col23 (cdr (assoc 62 mpn23)))
  (if (= lt23 nil) (setq lt23 "bylayer"))
  (if (= lt23 "byblock") (setq lt23 "byblock"))
  (if (= col23 nil) (setq col23 "bylayer"))
  (if (= col23 "byblock") (setq col23 "byblock"))
  (command "change" list23 "" "p" "la" lay23 "c" col23 "lt" lt23 "")
  (prompt "\nFinished.")
  (setvar "cmdecho" 1)
  (princ)
)

;*********************

(defun c:ml (/ list13 lri13 mpn13 lay13)
  (prompt "\nSelect objects: ")
  (setvar "cmdecho" 0)
  (command "select" "au" pause)
  (setq list13 (ssget "p"))
  (setq lri13 (entsel "\nSelect entity to match: "))
  (command "undo" "mark")
  (setq mpn13 (entget (car lri13)))
  (setq lay13 (cdr (assoc 8 mpn13)))
  (command "change" list13 "" "p" "la" lay13 "")
  (princ)
  (setvar "cmdecho" 1)
)

;*********************

(defun c:CRT (/ A B C D)
  (setvar "CMDECHO" 0)
  (prompt "\nFor rotated copy")
  (ssget)
  (setq A (getpoint "\nBase point: "))
  (command "ID" A)
  (setq B (getpoint "\nNew point <Return> if same as Base point> "))
  (if (= B nil) (setq B A))
;  (setq D (/ (* (getangle B "\nRotation angle <0>: ") 180.0) pi))
  (command "COPY" "P" "" A A)
  (command "MOVE" "P" "" A B)
  (command "ROTATE" "P" "" B pause)
  (setvar "CMDECHO" 1)
)

;*********************

(defun c:lac (/ co43 obj23 la23)
   (setvar "cmdecho" 0)
   (setq co43 (getstring "\nNew color : "))
   (setq obj23 (car (entsel "\nPick object on desired layer: ")))
   (if obj23 (progn
             (setq obj23 (entget obj23))
             (setq la23 (cdr (assoc 8 obj23)))
             (command "layer" "c" co43 la23 "")
          )
    )
   (prompt (strcat  "\nLayer has changed..." la23))
   (setvar "cmdecho" 1)
   (princ)
)

;*********************
(Defun c:MT ()
	(setq d1 (getpoint )) 
        (setq d2 (getpoint d1 ))
        (setq goc(angle d1 d2))
        (setq d3 (polar d1 goc 2))
        (COMMAND "osnap" "none")
        (COMMAND "layer" "set" 1 "")
        (COMMAND "Pline" d1 "w" 0 1 d3 "w" 0 0 d2 )
)	

;**********************
