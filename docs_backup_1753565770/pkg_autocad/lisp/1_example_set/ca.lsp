;--- Macro to convert a selection of text entities to
;--- lower or upper case. Non-text entities will be ignored.
(defun start()
      (setq sc (getvar "dimtxt") ) 
      (setq _lup (getvar "luprec"))
      (setq _ocho (getvar "cmdecho"))
      (setq _osmode (getvar "osmode"))
      (setvar "osmode" 243)
      (setvar "cmdecho" 0)
      (setvar "luprec" 0)
)
(defun finish()
(setvar "osmode" _osmode)
(setvar "luprec" _lup)
(setvar "cmdecho" _ocho)
)
(defun da (a)
(/ (* a 180.0) pi)
)
(defun rad (a)
(* pi (/ a 180.0))
)
(defun mk (f)
(setq m (* f f))
(setq m (* pi m))
(setq m (* m 0.0078))
(/ m 4)
)
(defun tx (p te)
(command "text" "j" "mc" p sc "0" te)
)
(defun setp(p)
(setq p1 (polar p (rad 270) (* 3.0 sc)))
(setq p2 (polar p1 (rad 0) (* 6.8 sc)))
(setq p3 (polar p2 (rad 0) (* 7 sc)))
(setq p4 (polar p3 (rad 0) (* 5 sc)))
(setq p5 (polar p4 (rad 0) (* 8.2 sc)))
(setq p6 (polar p5 (rad 0) (* 9.2 sc)))
(setq p7 (polar p1 (rad 176) (* 14.5 sc)))
;(command "line" p4 p5 "")
)
(defun ca1()
         (PROMPT"\nSelect Line lenght :")
         (SETQ SET (SSGET))
    (IF (AND(= "LINE" (CDR (ASSOC 0 (SETQ A (ENTGET (SSNAME SET 0))))))
        )
      (progn
         (SETQ L1 (ASSOC 10 A))
         (SETQ p1 (CDR L1))
         (SETQ L2 (ASSOC 11 A))
         (SETQ p2 (CDR L2))
         (SETQ d (distance p1 p2))
         (setq dk (getdist "Duong kinh: <10>"))
               (if (= dk nill) (setq dk 10))
         (setq lt (getdist "Loai moc <100> :"))
         (if (= lt nill) (setq lt 100))
         (SETQ cd (+ d (* 2 lt)))
      ) 
   )
)
(defun ca3()
(setq po (getpoint " Enter base point" ))
(setvar "luprec" 0)
(setq qty (rtos qty))
(setq qty (atoi qty))
(setvar "luprec" 2)
(setq tsl ( * qty 1))        ;tong so luong
(setq td (/ (* cd tsl) 1000)); tong chieu dai
(setq ma (* td (mk dk))) 
(setvar "luprec" 0)       
(setq dk (rtos dk) 
      cd (rtos cd) 
      qty (rtos qty) 
      d (rtos d) 
      tsl (rtos tsl))
(setvar "luprec" 2)
(setq td (rtos td) 
      ma (rtos ma))
(setp po)
(tx p1 dk) (tx p2 cd) (tx p3 qty) 
(tx p4 qty) (tx p5 td) (tx p6 ma) (tx p7 d)
)
(defun total()
         (SETQ L1 (ASSOC 10 A))
         (SETQ p1 (CDR L1))
         (SETQ L2 (ASSOC 11 A))
         (SETQ p2 (CDR L2))
         (SETQ d1 (distance p1 p2))
         (redraw (cdr(assoc -1 a)) 3)
         ;(prompt (strcat "\nDoan thu: " (rtos (+ INDEX 1)) ))
         ;(setq n (getdist  "\nKhoan cach <200>: "))
          (setq n 200)
         ;(if (= n nill) (setq n 200))
         (redraw (cdr(assoc -1 A)) 1)
         (setq qty (+ qty (+ (/ d1 n) 1)))
         (setq tolen (+ tolen d1))
    ; (command "regen" "")
)
(defun C:ca()
(start)
 (SETQ d1 0 quant 0 qty 0 tolen 0)
 (PROMPT"\nSelect ")
 (SETQ SET (SSGET))
 (SETQ QUANT (SSLENGTH SET))
 (SETQ INDEX 0)
  (WHILE (< INDEX QUANT)
    (IF (AND(= "LINE" (CDR (ASSOC 0 (SETQ A (ENTGET (SSNAME SET INDEX))))))
        )
    (PROGN
         (total)
    )
   )  
  (SETQ INDEX (+ INDEX 1))   
 )
;(ca1) (ca3)
;(princ qty) 
(prompt (strcat "\nTong chieu dai: "(rtos tolen)))
    (progn
        (setq casio (load_dialog "ca.DCL"))
	(if (not (new_dialog "casio" casio)) (exit))
        (set_tile "qty" (rtos quant))
        (set_tile "lenght" (rtos tolen))
        (action_tile "accept" "(setq flag 1) (done_dialog)")
        (start_dialog)
	(unload_dialog casio)
     ) 	
(finish) 
(command "redraw" "")
)
(defun C:cas()
(start)
       (prompt "\nKhoang cach bo tri thesp: ")
       (setq p1 (getpoint  "\nDiem dau : "))
       (setq p2 (getpoint  "\nDiem cuoi : " p1))
       (SETQ d (distance p1 p2))
       (setq n (getdist  "\nKhoan cach <200>: "))
            (if (= n nill) (setq n 200))
       (setq qty (+ (/ d n) 1))
       (prompt "\nChieu dai thanh: ")
   (setq p1 (getpoint  "\nDiem dau : "))
   (setq p2 (getpoint  "\nDiem cuoi : " p1))
   (SETQ d (distance p1 p2))
         (setq dk (getdist "Duong kinh: <10>"))
               (if (= dk nill) (setq dk 10))
         (setq lt (getdist "Loai moc <100> :"))
         (if (= lt nill) (setq lt 100))
         (SETQ cd (+ d (* 2 lt)))
(ca3)
(finish)
)
(defun C:cs()
(start)
       (prompt "\nKhoang cach bo tri thep: ")
       (setq p1 (getpoint  "\nDiem dau : "))
       (setq p2 (getpoint  "\nDiem cuoi : " p1))
       (SETQ d (distance p1 p2))
       (setq n (getdist  "\nKhoan cach <200>: "))
            (if (= n nill) (setq n 200))
       (setq qty (+ (/ d n) 1))
      (setq qty (rtos qty))
      (prompt "\nSo Khoang cach bo tri thep: ")
 (progn
        (setq casio (load_dialog "ca.DCL"))
	(if (not (new_dialog "casio" casio)) (exit))
        (set_tile "lenght" (rtos n))
        (set_tile "qty" qty)
        (action_tile "accept" "(setq flag 1) (done_dialog)")
        (start_dialog)
	(unload_dialog casio)
     ) 	
(print qty)
(princ)
(princ)
(finish)
)

(defun C:sa()
(start)
       (setq d (getdist "\nKhoang cach bo tri thep: "))
             (setq n (getdist  "\nKhoan cach <200>: "))
            (if (= n nill) (setq n 200))
       (setq qty (+ (/ d n) 1))
      (setq qty (rtos qty))
       (prompt "\nSo Khoang cach bo tri thep: ")
 (progn
        (setq casio (load_dialog "ca.DCL"))
	(if (not (new_dialog "casio" casio)) (exit))
       (set_tile "num" (rtos n))
        (set_tile "demsty" qty)
        (action_tile "accept" "(setq flag 1) (done_dialog)")
        (start_dialog)
	(unload_dialog casio)
     ) 	
(finish)
)

(defun C:TONG()
(start)
 (SETQ d1 0 quant 0 qty 0 tolen 0)
 (PROMPT"\nSelect ")
 (SETQ SET (SSGET))
 (SETQ QUANT (SSLENGTH SET))
 (SETQ INDEX 0)
  (WHILE (< INDEX QUANT)
    
     (setq f1 (entget(ssname f1 (setq INDEX (1- INDEX)))))
     (setq name (cdr (assoc 1 f1)))
     (setq t1 (atoi name)) ;length 
  (SETQ INDEX (+ INDEX 1))   
 )
  (SETQ QTY (+ QTY NAME))
;(ca1) (ca3)
;(princ qty) 
(prompt (strcat "\nTong chieu dai: "(rtos tolen)))
    (progn
        (setq casio (load_dialog "ca.DCL"))
	(if (not (new_dialog "casio" casio)) (exit))
        (set_tile "qty" (rtos quant))
        (set_tile "lenght" (rtos tolen))
        (action_tile "accept" "(setq flag 1) (done_dialog)")
        (start_dialog)
	(unload_dialog casio)
     ) 	
(finish) 
(command "redraw" "")
)
