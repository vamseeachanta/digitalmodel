;
;
;; Copyright by Do Manh Hien 44x5                       
; ==============================================================================
;
;                       CHUONG TRINH THONG KE COT THEP
;
;                                 THEP.LSP
;
; ==============================================================================
;
;
; * Chuong trinh duoc lap bang ngon ngu AUTOLISP.
; ------------------------------------------------------------------------------
(vmon)
; ------------------------------------------------------------------------------
; Chu y: Chuong trinh THONG KE COT THEP phai chay sau chuong trinh LAP BANG
;
; ------------------------------------------------------------------------------
; COMMAND function: THEP ( Ham so chinh cua chuong trinh )
;
(defun C:THEP (/ Cm Bl Pw Key T1 T2 T3 T4 T5 T6 T7 
a1 a2 a3 a33 a4 a5 a6 a7 a8 a9 b1 b2 b3 b4 b5 b6 b7 b8 b9 b10 b11 b12 b13 b14 
b15 b16 b17 b18 b19 b20 b21 b22 b23 b24 b25 b26 b27 b28 b29 b30 b31 
N1 N2 N3 H3 H4 H5 H6 H7 
HN1 HN2 HN3 
S3 S4 S5 S6 S7 ST3 ST4 ST5 ST6 ST7 ST33 ST55 ST66 
SN1 SN2 SN3 SN11 SN22 SN33 SNN1 SNN2 SNN3 
number3 number4 number5 number6 number7 numbern1 numbern2 numbern3 
index3 index4 index5 index6 index7 lisaux inden1 inden2 inden3 
Position3 Position4 Position5 Position6 Position7 Positionn1 Positionn2 Positionn3 
Dau4 Cuoi4 Dau6 Cuoi6 Dau7 Cuoi7)
 (setq Cm (getvar "CMDECHO"))
 (setq Bl (getvar "BLIPMODE"))
 (setq Pw (getvar "PLINEWID"))
 (setvar "CMDECHO" 0)
 (setvar "BLIPMODE" 0)
 (initget 7)
 (setq T1 (getstring "\nSo hieu thep:"))
 (initget 1)
 (setq a1 (getpoint "\nChon diem bat dau (diem goc trai, ben tren cua o so hieu):"))
 (setq a2 (polar a1 (/ (* Pi 7) 4) (* 7 (sqrt 2))))
 (command "Circle" a2 "3")
 (command "Text" "m" a2 "3" "0" T1)
 (setq a3 (polar a2 0 8.5))
 (setq a33 (polar a3 0 3))
 (initget 7)
 (setq T2 (getint "\nDuong kinh thep Fi(mm)="))
 (command "Text" a3 "3" "0" "%%C")
 (command "Text" a33 "3" "0" T2)
 (initget 7)
 (setq ST33 (getreal "\nSo luong thep="))
 (setq ST3 (rtos (/ ST33 1)))
 (setq index3 1)
 (setq lisaux nil)
 (setq s3 ".")
 (setq number3 0)
 (while (< Index3 (+ (strlen ST3) 1))
 (setq H3 (substr ST3 Index3 1))
 (setq Index3 (+ 1 Index3))
       (if (= H3 s3)
       (setq Position3 (- Index3 1))
       )
 )
 (setq T3 (substr ST3 1 (- Position3 1)))
 (setq a4 (polar a2 0 84.5))
 (setq a5 (polar a4 0 92.5))
 (setq a6 (polar a4 0 25.5))
 (setq a7 (polar a6 0 33.5))
 (setq a8 (polar a5 0 33.5))
 (command "Text" "m" a4 "3" "0" T3)
 (setq ST44 (/ (* 785 Pi T2 T2) 400000))
 (setq ST4 (rtos (+ (/ (* 785 Pi T2 T2) 400000) 0.0005)))
 (setq index4 1)
 (setq lisaux nil)
 (setq s4 ".")
 (setq number4 0)
 (while (< Index4 (+ (strlen ST4) 1))
 (setq H4 (substr ST4 Index4 1))
 (setq Index4 (+ 1 Index4))
       (if (= H4 s4)
       (setq Position4 (- Index4 1))
       )
 )
 (setq Dau4 (substr ST4 1 Position4))
 (setq Cuoi4 (substr ST4 (+ Position4 1) 3))
 (setq T4 (strcat Dau4 Cuoi4))
 (command "Text" "M" a5 "3" "0" T4)
 (initget "Thep Moc Am L U Dai Cau Bat")
 (setq Key (getkword "\nThep thang/2 Moc/thep Am/hinh L/hinh U/cot Dai/moc Cau/hinh Bat ky:"))
 (cond
  ((= Key "Thep") (Thep))
  ((= Key "Moc") (Moc))
  ((= Key "Am") (Am))
  ((= Key "L") (L))
  ((= Key "U") (U))
  ((= Key "Dai") (Dai))
  ((= Key "Cau") (Cau))
  ((= Key "Bat") (Bat))
 )
 (command "Text" "m" a6 "3" "0" T5)
 (setq ST66 (/ (* ST33 ST55) 1000))
 (setq ST6 (rtos (/ (* ST33 ST55) 1000)))
 (setq index6 1)
 (setq lisaux nil)
 (setq s6 ".")
 (setq number6 0)
 (while (< Index6 (+ (strlen ST6) 1))
 (setq H6 (substr ST6 Index6 1))
 (setq Index6 (+ 1 Index6))
       (if (= H6 s6)
       (setq Position6 (- Index6 1))
       )
 )
 (setq Dau6 (substr ST6 1 Position6))
 (setq Cuoi6 (substr ST6 (+ Position6 1) 3))
 (setq T6 (strcat Dau6 Cuoi6))
 (command "Text" "M" a7 "3" "0" T6)
 (setq ST7 (rtos (* ST44 ST66)))
 (setq index7 1)
 (setq lisaux nil)
 (setq s7 ".")
 (setq number7 0)
 (while (< Index7 (+ (strlen ST7) 1))
 (setq H7 (substr ST7 Index7 1))
 (setq Index7 (+ 1 Index7))
       (if (= H7 s7)
       (setq Position7 (- Index7 1))
       )
 )
 (setq Dau7 (substr ST7 1 Position7))
 (setq Cuoi7 (substr ST7 (+ Position7 1) 3))
 (setq T7 (strcat Dau7 Cuoi7))
 (command "Text" "m" a8 "3" "0" T7)
 (setq a9 (polar a2 0 69))
 (command "Text" "m" a9 "2.5" "0" "thanh")
 (setvar "CMDECHO" Cm)
 (setvar "BLIPMODE" Bl)
)
;;; Thong ke cot thep
;;;
(defun Thep ()
 (initget 1)
 (setq b1 (polar a1 (* 1.91976 Pi) 34.0771))
 (setq b2 (polar b1 0 27))
 (setq b3 (polar b1 0 13.5))
 (setq b4 (polar b3 (/ Pi 2) 2))
 (command "Plinewid" "0")
 (command "Color" "1")
 (command "Pline" b1 b2 "")
 (command "Color" "7")
 (initget 7)
 (setq ST55 (getreal "\nChieu dai thanh thep (mm)="))
 (setq ST5 (rtos (/ ST55 1)))
 (setq index5 1)
 (setq lisaux nil)
 (setq s5 ".")
 (setq number5 0)
 (while (< Index5 (+ (strlen ST5) 1))
 (setq H5 (substr ST5 Index5 1))
 (setq Index5 (+ 1 Index5))
       (if (= H5 s5)
       (setq Position5 (- Index5 1))
       )
 )
 (setq T5 (substr ST5 1 (- Position5 1)))
 (command "Text" "m" b4 "1.5" "0" T5)
)
;;; Thong ke cot thep
;;;
(defun Moc ()
 (initget 1)
 (setq b5 (polar a1 (* Pi 1.93186) 35.3058))
 (setq b6 (polar b5 0 1.5))
 (setq b7 (polar b5 (/ (* Pi 3) 2) 1.5))
 (setq b8 (polar b7 0 24))
 (setq b9 (polar b8 (/ Pi 2) 1.5))
 (setq b10 (polar b9 Pi 1.5))
 (setq b11 (polar b7 0 12))
 (setq b12 (polar b11 (/ Pi 2) 2))
 (setq b13 (polar b5 (/ Pi 2) 2))
 (setq b14 (polar b9 (/ Pi 2) 2))
 (command "Plinewid" "0")
 (command "Color" "1")
 (command "Pline" b6 b5 "a" b7 "l" b8 "a" b9 "l" b10 "")
 (command "Color" "7")
 (initget 7)
 (setq SN11 (getreal "\nChieu dai moc (mm)="))
 (setq SN1 (rtos (/ SN11 1)))
 (setq inden1 1)
 (setq lisaux nil)
 (setq snn1 ".")
 (setq numbern1 0)
 (while (< Inden1 (+ (strlen SN1) 1))
 (setq HN1 (substr SN1 Inden1 1))
 (setq Inden1 (+ 1 Inden1))
       (if (= HN1 snn1)
       (setq Positionn1 (- Inden1 1))
       )
 )
 (setq N1 (substr SN1 1 (- Positionn1 1)))
 (command "Text" "m" b13 "1.5" "0" N1)
 (command "Text" "m" b14 "1.5" "0" N1)
 (initget 7)
 (setq SN22 (getreal "\nChieu dai doan giua thanh (mm)="))
 (setq SN2 (rtos (/ SN22 1)))
 (setq inden2 1)
 (setq lisaux nil)
 (setq snn2 ".")
 (setq numbern2 0)
 (while (< Inden2 (+ (strlen SN2) 1))
 (setq HN2 (substr SN2 Inden2 1))
 (setq Inden2 (+ 1 Inden2))
       (if (= HN2 snn2)
       (setq Positionn2 (- Inden2 1))
       )
 )
 (setq N2 (substr SN2 1 (- Positionn2 1)))
 (command "Text" "m" b12 "1.5" "0" N2)
 (setq ST55 (+ SN22 (* SN11 2)))
 (setq ST5 (rtos (+ SN22 (* SN11 2))))
 (setq index5 1)
 (setq lisaux nil)
 (setq s5 ".")
 (setq number5 0)
 (while (< Index5 (+ (strlen ST5) 1))
 (setq H5 (substr ST5 Index5 1))
 (setq Index5 (+ 1 Index5))
       (if (= H5 s5)
       (setq Position5 (- Index5 1))
       )
 )
 (setq T5 (substr ST5 1 (- Position5 1)))
)
;;; Thong ke cot thep
;;;
(defun Am ()
 (initget 1)
 (setq b15 (polar a1 (* 1.90683 Pi) 38.1215))
 (setq b16 (polar b15 (/ Pi 2) 5))
 (setq b17 (polar b16 0 20))
 (setq b18 (polar b15 0 20))
 (setq b19 (polar b16 0 10))
 (setq b20 (polar b15 (/ Pi 2) 2.5))
 (setq b21 (polar b20 0 20))
 (setq b22 (polar b19 (/ Pi 2) 2))
 (setq b23 (polar b20 Pi 1))
 (setq b24 (polar b21 0 1))
 (command "Plinewid" "0")
 (command "Color" "1")
 (command "Pline" b15 b16 b17 b18 "")
 (command "Color" "7")
 (initget 7)
 (setq SN11 (getreal "\nChieu dai doan thu nhat (mm)="))
 (setq SN1 (rtos (/ SN11 1)))
 (setq inden1 1)
 (setq lisaux nil)
 (setq snn1 ".")
 (setq numbern1 0)
 (while (< Inden1 (+ (strlen SN1) 1))
 (setq HN1 (substr SN1 Inden1 1))
 (setq Inden1 (+ 1 Inden1))
       (if (= HN1 snn1)
       (setq Positionn1 (- Inden1 1))
       )
 )
 (setq N1 (substr SN1 1 (- Positionn1 1)))
 (command "Text" "r" b23 "1.5" "0" N1)
 (command "Text" b24 "1.5" "0" N1)
 (initget 7)
 (setq SN22 (getreal "\nChieu dai doan giua thanh (mm)="))
 (setq SN2 (rtos (/ SN22 1)))
 (setq inden2 1)
 (setq lisaux nil)
 (setq snn2 ".")
 (setq numbern2 0)
 (while (< Inden2 (+ (strlen SN2) 1))
 (setq HN2 (substr SN2 Inden2 1))
 (setq Inden2 (+ 1 Inden2))
       (if (= HN2 snn2)
       (setq Positionn2 (- Inden2 1))
       )
 )
 (setq N2 (substr SN2 1 (- Positionn2 1)))
 (command "Text" "m" b22 "1.5" "0" N2)
 (setq ST55 (+ SN22 (* SN11 2)))
 (setq ST5 (rtos (+ SN22 (* SN11 2))))
 (setq index5 1)
 (setq lisaux nil)
 (setq s5 ".")
 (setq number5 0)
 (while (< Index5 (+ (strlen ST5) 1))
 (setq H5 (substr ST5 Index5 1))
 (setq Index5 (+ 1 Index5))
       (if (= H5 s5)
       (setq Position5 (- Index5 1))
       )
 )
 (setq T5 (substr ST5 1 (- Position5 1)))
)
;;; Thong ke cot thep
;;;
(defun L ()
 (initget 1)
 (setq b25 (polar a1 (* 1.91857 Pi) 33.5932))
 (setq b26 (polar b25 0 25))
 (setq b27 (polar b26 (/ Pi 2) 5))
 (setq b28 (polar b25 0 12.5))
 (setq b29 (polar b26 (/ Pi 2) 2.5))
 (setq b30 (polar b28 (/ (* Pi 3) 2) 2))
 (setq b31 (polar b29 0 1))
 (command "Plinewid" "0")
 (command "Color" "1")
 (command "Pline" b25 b26 b27 "")
 (command "Color" "7")
 (initget 7)
 (setq SN11 (getreal "\nChieu dai doan thu nhat (mm)="))
 (setq SN1 (rtos (/ SN11 1)))
 (setq inden1 1)
 (setq lisaux nil)
 (setq snn1 ".")
 (setq numbern1 0)
 (while (< Inden1 (+ (strlen SN1) 1))
 (setq HN1 (substr SN1 Inden1 1))
 (setq Inden1 (+ 1 Inden1))
       (if (= HN1 snn1)
       (setq Positionn1 (- Inden1 1))
       )
 )
 (setq N1 (substr SN1 1 (- Positionn1 1)))
 (command "Text" "m" b30 "1.5" "0" N1)
 (initget 7)
 (setq SN22 (getreal "\nChieu dai doan thu hai (mm)="))
 (setq SN2 (rtos (/ SN22 1)))
 (setq inden2 1)
 (setq lisaux nil)
 (setq snn2 ".")
 (setq numbern2 0)
 (while (< Inden2 (+ (strlen SN2) 1))
 (setq HN2 (substr SN2 Inden2 1))
 (setq Inden2 (+ 1 Inden2))
       (if (= HN2 snn2)
       (setq Positionn2 (- Inden2 1))
       )
 )
 (setq N2 (substr SN2 1 (- Positionn2 1)))
 (command "Text" b31 "1.5" "0" N2)
 (setq ST55 (+ SN22 SN11))
 (setq ST5 (rtos (+ SN22 SN11)))
 (setq index5 1)
 (setq lisaux nil)
 (setq s5 ".")
 (setq number5 0)
 (while (< Index5 (+ (strlen ST5) 1))
 (setq H5 (substr ST5 Index5 1))
 (setq Index5 (+ 1 Index5))
       (if (= H5 s5)
       (setq Position5 (- Index5 1))
       )
 )
 (setq T5 (substr ST5 1 (- Position5 1)))
)
;;; Thong ke cot thep
;;;
(defun U ()
 (initget 1)
 (setq b15 (polar a1 (* 1.91859 Pi) 37.716))
 (setq b16 (polar b15 (/ Pi 2) 5))
 (setq b17 (polar b16 0 20))
 (setq b18 (polar b15 0 20))
 (setq b19 (polar b15 0 10))
 (setq b20 (polar b15 (/ Pi 2) 2.5))
 (setq b21 (polar b20 0 20))
 (setq b22 (polar b19 (/ (* Pi 3) 2) 2))
 (setq b23 (polar b20 Pi 1))
 (setq b24 (polar b21 0 1))
 (command "Plinewid" "0")
 (command "Color" "1")
 (command "Pline" b16 b15 b18 b17 "")
 (command "Color" "7")
 (initget 7)
 (setq SN11 (getreal "\nChieu dai doan thu nhat (mm)="))
 (setq SN1 (rtos (/ SN11 1)))
 (setq inden1 1)
 (setq lisaux nil)
 (setq snn1 ".")
 (setq numbern1 0)
 (while (< Inden1 (+ (strlen SN1) 1))
 (setq HN1 (substr SN1 Inden1 1))
 (setq Inden1 (+ 1 Inden1))
       (if (= HN1 snn1)
       (setq Positionn1 (- Inden1 1))
       )
 )
 (setq N1 (substr SN1 1 (- Positionn1 1)))
 (initget 7)
 (setq SN22 (getreal "\nChieu dai doan giua thanh (mm)="))
 (setq SN2 (rtos (/ SN22 1)))
 (setq inden2 1)
 (setq lisaux nil)
 (setq snn2 ".")
 (setq numbern2 0)
 (while (< Inden2 (+ (strlen SN2) 1))
 (setq HN2 (substr SN2 Inden2 1))
 (setq Inden2 (+ 1 Inden2))
       (if (= HN2 snn2)
       (setq Positionn2 (- Inden2 1))
       )
 )
 (setq N2 (substr SN2 1 (- Positionn2 1)))
 (initget 7)
 (setq SN33 (getreal "\nChieu dai doan thu ba (mm)="))
 (setq SN3 (rtos (/ SN33 1)))
 (setq inden3 1)
 (setq lisaux nil)
 (setq snn3 ".")
 (setq numbern3 0)
 (while (< Inden3 (+ (strlen SN3) 1))
 (setq HN3 (substr SN3 Inden3 1))
 (setq Inden3 (+ 1 Inden3))
       (if (= HN3 snn3)
       (setq Positionn3 (- Inden3 1))
       )
 )
 (setq N3 (substr SN3 1 (- Positionn3 1)))
 (command "Text" "r" b23 "1.5" "0" N1)
 (command "Text" "m" b22 "1.5" "0" N2)
 (command "Text" b24 "1.5" "0" N3)
 (setq ST55 (+ SN22 SN11 SN33))
 (setq ST5 (rtos (+ SN22 SN11 SN33)))
 (setq index5 1)
 (setq lisaux nil)
 (setq s5 ".")
 (setq number5 0)
 (while (< Index5 (+ (strlen ST5) 1))
 (setq H5 (substr ST5 Index5 1))
 (setq Index5 (+ 1 Index5))
       (if (= H5 s5)
       (setq Position5 (- Index5 1))
       )
 )
 (setq T5 (substr ST5 1 (- Position5 1)))
)
;;; Thong ke cot thep
;;;
(defun Dai ()
 (initget 1)
 (setq b15 (polar a1 (* 1.90408 Pi) 38.746))
 (setq b16 (polar b15 (/ Pi 2) 6))
 (setq b17 (polar b16 0 16))
 (setq b18 (polar b15 0 16))
 (setq b19 (polar b17 (/ Pi 2) 3))
 (setq b20 (polar b17 0 3))
 (setq b21 (polar b16 0 8))
 (setq b22 (polar b21 (/ Pi 2) 2))
 (setq b23 (polar b18 (/ Pi 2) 2))
 (setq b24 (polar b23 0 1))
 (setq b25 (polar b17 (/ Pi 4) (sqrt 2)))
 (command "Plinewid" "0")
 (command "Color" "1")
 (command "Pline" b19 b18 b15 b16 b20 "")
 (command "Color" "7")
 (initget 7)
 (setq SN11 (getreal "\nChieu dai doan thu nhat cua dai (mm)="))
 (setq SN1 (rtos (/ SN11 1)))
 (setq inden1 1)
 (setq lisaux nil)
 (setq snn1 ".")
 (setq numbern1 0)
 (while (< Inden1 (+ (strlen SN1) 1))
 (setq HN1 (substr SN1 Inden1 1))
 (setq Inden1 (+ 1 Inden1))
       (if (= HN1 snn1)
       (setq Positionn1 (- Inden1 1))
       )
 )
 (setq N1 (substr SN1 1 (- Positionn1 1)))
 (initget 7)
 (setq SN22 (getreal "\nChieu dai doan thu hai cua dai (mm)="))
 (setq SN2 (rtos (/ SN22 1)))
 (setq inden2 1)
 (setq lisaux nil)
 (setq snn2 ".")
 (setq numbern2 0)
 (while (< Inden2 (+ (strlen SN2) 1))
 (setq HN2 (substr SN2 Inden2 1))
 (setq Inden2 (+ 1 Inden2))
       (if (= HN2 snn2)
       (setq Positionn2 (- Inden2 1))
       )
 )
 (setq N2 (substr SN2 1 (- Positionn2 1)))
 (initget 7)
 (setq SN33 (getreal "\nChieu dai 1 doan neo buoc (co 2 doan neo)="))
 (setq SN3 (rtos (/ SN33 1)))
 (setq inden3 1)
 (setq lisaux nil)
 (setq snn3 ".")
 (setq numbern3 0)
 (while (< Inden3 (+ (strlen SN3) 1))
 (setq HN3 (substr SN3 Inden3 1))
 (setq Inden3 (+ 1 Inden3))
       (if (= HN3 snn3)
       (setq Positionn3 (- Inden3 1))
       )
 )
 (setq N3 (substr SN3 1 (- Positionn3 1)))
 (command "Text" "m" b22 "1.5" "0" N1)
 (command "Text" b24 "1.5" "0" N2)
 (command "Text" b25 "1.5" "0" N3)
 (setq ST55 (+ SN22 SN11 SN33))
 (setq ST5 (rtos (+ SN22 SN11 SN33)))
 (setq index5 1)
 (setq lisaux nil)
 (setq s5 ".")
 (setq number5 0)
 (while (< Index5 (+ (strlen ST5) 1))
 (setq H5 (substr ST5 Index5 1))
 (setq Index5 (+ 1 Index5))
       (if (= H5 s5)
       (setq Position5 (- Index5 1))
       )
 )
 (setq T5 (substr ST5 1 (- Position5 1)))
)
;;; Thong ke cot thep
;;;
(defun Cau ()
 (initget 7)
 (setq ST55 (getreal "\nChieu dai toan bo thanh thep (mm)="))
 (setq ST5 (rtos (* ST55 1)))
 (setq index5 1)
 (setq lisaux nil)
 (setq s5 ".")
 (setq number5 0)
 (while (< Index5 (+ (strlen ST5) 1))
 (setq H5 (substr ST5 Index5 1))
 (setq Index5 (+ 1 Index5))
       (if (= H5 s5)
       (setq Position5 (- Index5 1))
       )
 )
 (setq T5 (substr ST5 1 (- Position5 1)))
 (initget 1)
 (setq b1 (polar a1 (* 1.93333 Pi) 44.5949))
 (setq b2 (polar b1 Pi 2))
 (setq b3 (polar b2 (* (/ Pi 2) 3) 1.5))
 (setq b4 (polar b3 0 3.75))
 (setq b5 (polar b4 (/ Pi 2) 6.25))
 (setq b6 (polar b1 0 5.75))
 (setq b7 (polar b6 0 2))
 (setq b8 (polar b7 (* (/ Pi 2) 3) 1.5))
 (setq b9 (polar b4 0 2.25))
 (setq b10 (polar b5 0 2.25))
 (command "Plinewid" "0")
 (command "Color" "1")
 (command "Pline" b1 b2 "a" b3 "l" b4 b5 "")
 (command "Pline" b6 b7 "a" b8 "l" b9 b10 "a" b5 "")
 (command "Color" "7")
)
;;; Thong ke cot thep
;;;
(defun Bat ()
 (initget 7)
 (setq ST55 (getreal "\nChieu dai toan bo thanh thep (mm)="))
 (setq ST5 (rtos (* ST55 1)))
 (setq index5 1)
 (setq lisaux nil)
 (setq s5 ".")
 (setq number5 0)
 (while (< Index5 (+ (strlen ST5) 1))
 (setq H5 (substr ST5 Index5 1))
 (setq Index5 (+ 1 Index5))
       (if (= H5 s5)
       (setq Position5 (- Index5 1))
       )
 )
 (setq T5 (substr ST5 1 (- Position5 1)))
)
; ------------------------------------------------------------------------------

(princ "  THEP loaded.  ")
(princ)


-----------------------------------------------------------------------
TRA THEP
; GET_D function:
;
(defun Get_D ()
 (set_tile "error" "")
 (setq D (get_tile "DuongKinh"))
 (setq TRATHEP:D (distof D))
 (setq TRATHEP:T (* 7850 (/ (* Pi TRATHEP:D TRATHEP:D) 4000000)))
 (set_tile "TrongLuong" (rtos TRATHEP:T 2))
 (if (<= TRATHEP:D 0)
     (Verify)
 )
)
; ------------------------------------------------------------------------------
; GET_SO function:
;
(defun Get_SO ()
 (set_tile "error" "")
 (setq SO (get_tile "SoThanh"))
 (setq TRATHEP:SO (fix (distof SO)))
 (setq TRATHEP:F (* TRATHEP:SO (/ (* Pi TRATHEP:D TRATHEP:D) 400)))
 (set_tile "DienTich" (rtos TRATHEP:F 2))
 (if (<= TR:SO 0)
     (Verify)
 )
)
; ------------------------------------------------------------------------------
; VERIFY function
;
(defun Verify ()
 (set_tile "error" "")
 (if (and (= ok_para 1) (not (> TRATHEP:D 0)))
     (progn (set_tile "error" "CHU Y: Vao tri so Fi(mm) sai.")
            (setq ok_para 0) ) )
 (if (and (= ok_para 1) (not (> TRATHEP:SO 3)))
     (progn (set_tile "error" "CHU Y: Vao so thanh thep sai.")
            (setq ok_para 0) ) )
 ok_para
)
; ------------------------------------------------------------------------------
; SETLOC_TRATHEP function:
;
(defun Setloc_TRATHEP ()

 (if (not TRATHEP:D) (setq TRATHEP:D 12))
 (set_tile "DuongKinh" (setq D (rtos TRATHEP:D 2)))

 (if (not TRATHEP:SO) (setq TRATHEP:SO 6))
 (set_tile "SoThanh" (setq So (rtos TRATHEP:SO 2)))

 (Verify)
)
; ------------------------------------------------------------------------------
; RESTORE function:
;
(defun Restore ()
 (setvar "CMDECHO" OldCmd)
 (setvar "PICKBOX" OldPic)
 (setq *ERROR* Olderr)
)
; ------------------------------------------------------------------------------
; COMMAND function: TRATHEP (Ham so chinh cua chuong trinh)
; ------------------------------------------------------------------------------
;
(defun C:TRATHEP (/ OldCmd OldPic Olderr Dial D So TRATHEP:SO TRATHEP:T)
 (setq OldCmd (getvar "CMDECHO")
       OldPic (getvar "PICKBOX")
       Olderr *ERROR*
 )
 (setvar "CMDECHO" 0)
 (setvar "PICKBOX" 0)

 (defun *ERROR* (Msg)
  (princ "\nError: ") (princ Msg)
  (unload_dialog Dial)
  (Restore)
  (princ)
 )

 (setq Dial (load_dialog "TRATHEP.DCL"))
 (if (not (new_dialog "TRATHEP" Dial))
     (progn (Restore)
            (exit)  )
 )
 (Setloc_TRATHEP)
 (action_tile "DuongKinh" "(Get_D)")
 (action_tile "SoThanh" "(Get_So)")
 (start_dialog)
 (unload_dialog Dial)
 (Restore)
 (princ)
)
; ==============================================================================
(princ "  TRATHEP loaded.  ")
(princ)
